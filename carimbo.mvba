Attribute VB_Name = "carimba"
Sub carimbo_cel()
    Set classe = New cria_cell
    Dim formu As f_carimb
    Set formu = New f_carimb
    Set classe.parente = formu
    CommandState.StartPrimitive classe
    formu.Show 0
    
    'CommandState.SetLocateCursor



End Sub

Sub teste()
    'determina a extensao do desenho
    tamanho = ActiveModelReference.Range(True)
    tam_x = tamanho.High.X - tamanho.Low.X
    tam_y = tamanho.High.Y - tamanho.Low.Y
    tam_z = tamanho.High.Z - tamanho.Low.Z
    
    max = tam_x
    If max < tam_y Then max = tam_y
    
    ShowCommand "Ponto"
    ShowPrompt "x=" & Str(tam_x) & ", y=" & Str(tam_y)
End Sub

Attribute VB_Name = "cria_cell"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Public parente As f_carimb

Private m_nPoints As Integer

Private Sub IPrimitiveCommandEvents_Cleanup()

End Sub

Private Sub IPrimitiveCommandEvents_DataPoint(Point As Point3d, ByVal View As View)
    If IsCellLibraryAttached Then
        Dim escala As Point3d
        Dim rot As Matrix3d
        Dim ang As Double
        
        escala.X = CDbl(parente.escala.Value)
        escala.Y = CDbl(parente.escala.Value)
        escala.Z = CDbl(parente.escala.Value)
        
        ang = CDbl(parente.rotacao.Value) * Pi / 180
        
        ' Matriz de rotação
        rot = Matrix3dFromAxisAndRotationAngle(2, ang)
    
        Dim carimbo As CellElement
        
        If parente.ob_visto.Value = True Then
            Set carimbo = CreateCellElement2("visto", Point, escala, True, rot)
        ElseIf parente.ob_visto_cn.Value = True Then
            Set carimbo = CreateCellElement2("c_notas", Point, escala, True, rot)
        ElseIf parente.ob_n_atende.Value = True Then
            Set carimbo = CreateCellElement2("revisao", Point, escala, True, rot)
        ElseIf parente.ob_pc.Value = True Then
            Set carimbo = CreateCellElement2("pc", Point, escala, True, rot)
        End If
        
        
        Dim oComponents As ElementEnumerator
        Set oComponents = carimbo.Drop
        Do While oComponents.MoveNext
            Dim oElement As Element
            Set oElement = oComponents.Current
            ActiveModelReference.AddElement oElement
            
            If oElement.IsTextElement Then
                Dim eleText As TextElement
                
                Set eleText = oElement.AsTextElement
                If eleText.Text = "01/01/1970" Then
                    eleText.Text = Date
                    eleText.Rewrite
                End If
                
            
            End If
            
            
        Loop
    End If
    
    

End Sub


Private Sub IPrimitiveCommandEvents_Dynamics(Point As Point3d, ByVal View As View, ByVal DrawMode As MsdDrawingMode)
    If IsCellLibraryAttached Then
        Dim escala As Point3d
        Dim rot As Matrix3d
        Dim ang As Double
        
        escala.X = CDbl(parente.escala.Value)
        escala.Y = CDbl(parente.escala.Value)
        escala.Z = CDbl(parente.escala.Value)
        
        ang = CDbl(parente.rotacao.Value) * Pi / 180
        
        ' Matriz de rotação
        rot = Matrix3dFromAxisAndRotationAngle(2, ang)
    
        Dim carimbo As CellElement
        
        If parente.ob_visto.Value = True Then
            Set carimbo = CreateCellElement2("visto", Point, escala, True, rot)
        ElseIf parente.ob_visto_cn.Value = True Then
            Set carimbo = CreateCellElement2("c_notas", Point, escala, True, rot)
        ElseIf parente.ob_n_atende.Value = True Then
            Set carimbo = CreateCellElement2("revisao", Point, escala, True, rot)
        ElseIf parente.ob_pc.Value = True Then
            Set carimbo = CreateCellElement2("pc", Point, escala, True, rot)
        End If
        
        carimbo.Redraw DrawMode
    End If
End Sub

Private Sub IPrimitiveCommandEvents_Keyin(ByVal Keyin As String)

End Sub

Private Sub IPrimitiveCommandEvents_Reset()
    parente.Hide
    CommandState.StartDefaultCommand
End Sub

Private Sub IPrimitiveCommandEvents_Start()
    ShowCommand "Carimbo EP/EC"
    ShowPrompt "Selecione o ponto desejado"
    AttachCellLibrary "C:\ProgramData\Bentley\PowerDraft V8i (SELECTseries)\WorkSpace\Projects\Untitled\cell\carimbo.cel"
    CommandState.StartDynamics
    
    'determina a extensao do desenho
    tamanho = ActiveModelReference.Range(True)
    tam_x = tamanho.High.X - tamanho.Low.X
    tam_y = tamanho.High.Y - tamanho.Low.Y
    tam_z = tamanho.High.Z - tamanho.Low.Z
    
    
    max = tam_x
    If max < tam_y Then max = tam_y
    
    If max > 0 Then parente.escala.Value = CStr(Round(max / (841 * ActiveModelReference.MasterUnit.UnitsPerBaseNumerator / ActiveModelReference.MasterUnit.UnitsPerBaseDenominator), 4))
    parente.escala.SelStart = 0
    parente.escala.SelLength = Len(parente.escala.Text)
    
    'CommandState.EnableAccuSnap
End Sub

Attribute VB_Name = "f_carimb"
Attribute VB_Base = "0{B3181BC2-F1C3-449F-8FBD-131A2B044C54}{C7A97E3F-924A-44BC-9E59-F2603DCCC0ED}"
Attribute VB_GlobalNameSpace = False
Attribute VB_Creatable = False
Attribute VB_PredeclaredId = True
Attribute VB_Exposed = False
Attribute VB_TemplateDerived = False
Attribute VB_Customizable = False

Private Sub escala_Change()
    If Not escala.Value = "" Then
        If Not IsNumeric(escala.Value) Then
            escala.Value = "1"
            Cancel = True
        End If
    End If
End Sub

Private Sub escala_Exit(ByVal Cancel As MSForms.ReturnBoolean)
    If Not IsNumeric(escala.Value) Then
        escala.Value = "1"
        Cancel = True
    End If
End Sub

Private Sub rotacao_Change()
    If Not rotacao.Value = "" And Not rotacao.Value = "-" Then
        If Not IsNumeric(rotacao.Value) Then
            rotacao.Value = "0"
            Cancel = True
        End If
    End If
End Sub

Private Sub rotacao_Exit(ByVal Cancel As MSForms.ReturnBoolean)
    If Not IsNumeric(rotacao.Value) Then
        rotacao.Value = "0"
        Cancel = True
    End If
End Sub
