Attribute VB_Name = "abre_lista"
Sub executa()
    
    Load f_abre
    f_abre.Show 0
End Sub

Attribute VB_Name = "f_abre"
Attribute VB_Base = "0{2F8BC95D-C611-454B-B4AC-0864C2F5BC34}{C0B0985A-6D5A-4E95-B897-3E9B55884954}"
Attribute VB_GlobalNameSpace = False
Attribute VB_Creatable = False
Attribute VB_PredeclaredId = True
Attribute VB_Exposed = False
Attribute VB_TemplateDerived = False
Attribute VB_Customizable = False

'------------------------------------------------------------------------------------------------------
'  OBJETO E CONSTANTES PARA A JANELA DE DIALOGO DE ABRIR
'------------------------------------------------------------------------------------------------------

Option Explicit
 
Private Const OFN_ALLOWMULTISELECT = &H200
Private Const OFN_CREATEPROMPT = &H2000
Private Const OFN_ENABLEHOOK = &H20
Private Const OFN_ENABLETEMPLATE = &H40
Private Const OFN_ENABLETEMPLATEHANDLE = &H80
Private Const OFN_EXPLORER = &H80000                         '  new look commdlg
Private Const OFN_EXTENSIONDIFFERENT = &H400
Private Const OFN_FILEMUSTEXIST = &H1000
Private Const OFN_HIDEREADONLY = &H4
Private Const OFN_LONGNAMES = &H200000                       '  force long names for 3.x modules
Private Const OFN_NOCHANGEDIR = &H8
Private Const OFN_NODEREFERENCELINKS = &H100000
Private Const OFN_NOLONGNAMES = &H40000                      '  force no long names for 4.x modules
Private Const OFN_NONETWORKBUTTON = &H20000
Private Const OFN_NOREADONLYRETURN = &H8000
Private Const OFN_NOTESTFILECREATE = &H10000
Private Const OFN_NOVALIDATE = &H100
Private Const OFN_OVERWRITEPROMPT = &H2
Private Const OFN_PATHMUSTEXIST = &H800
Private Const OFN_READONLY = &H1
Private Const OFN_SHAREAWARE = &H4000
Private Const OFN_SHAREFALLTHROUGH = 2
Private Const OFN_SHARENOWARN = 1
Private Const OFN_SHAREWARN = 0
Private Const OFN_SHOWHELP = &H10
 
Private Type OPENFILENAME
        lStructSize As Long
        hwndOwner As LongPtr
        hInstance As LongPtr
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        flags As Long
        nFileOffset As Integer
        nFileExtension As Integer
        lpstrDefExt As String
        lCustData As LongPtr
        lpfnHook As LongPtr
        lpTemplateName As String
        '#if (_WIN32_WINNT >= 0x0500)
        pvReserved As LongPtr
        dwReserved As Long
        FlagsEx As Long
'#endif // (_WIN32_WINNT >= 0x0500)
End Type


'#If VBA7 Then
Private Declare PtrSafe Function GetOpenFileName Lib "comdlg32.dll" Alias "GetOpenFileNameA" (pOpenfilename As OPENFILENAME) As Long
'#Else
'Private Declare Function GetOpenFileName Lib "comdlg32.dll" Alias "GetOpenFileNameA" (pOpenfilename As OPENFILENAME) As Long
'#End If
 
Private Function AddBS(ByVal sPath As String) As String
'------------------------------------------------------------------------------------------------------
'  FUNCAO PARA ADICIONAR A BARRA AOS CAMINHOS
'------------------------------------------------------------------------------------------------------
    If Right$(sPath, 1) <> "\" Then sPath = sPath & "\"
    AddBS = sPath
End Function


Private Sub B_abre_Click()
Dim num_des As Integer
Dim i As Integer
Dim nome_arq As String

    num_des = 0

    For i = 0 To l_arquivos.ListCount - 1
        nome_arq = l_arquivos.List(i, 0) 'pega o caminho completo do arquivo
        
        If verifica_arq.ver_formato(nome_arq) Then
            OpenDesignFile nome_arq, False, msdV7ActionUpgradeToV8 'abre o arquivo
            num_des = num_des + 1
        End If
        
        
    Next i
    
    For i = 1 To num_des
        CadInputQueue.SendCommand "MODELHISTORY BACK"
    Next i
    
    MsgBox "Pronto! Desenhos abertos=" & num_des
End Sub

Private Sub b_adiciona_Click()
'------------------------------------------------------------------------------------------------------
'  ADICIONA ITENS NA LISTA DE ARQUIVOS
'------------------------------------------------------------------------------------------------------
    Dim tOPENFILENAME As OPENFILENAME
    Dim lResult As Long
    Dim vFiles As Variant
    Dim lIndex As Long, lStart As Long
    
    With tOPENFILENAME
        .lpstrTitle = "Escolha os arquivos"
        .flags = OFN_ALLOWMULTISELECT Or OFN_EXPLORER Or OFN_FILEMUSTEXIST Or OFN_LONGNAMES Or OFN_NOCHANGEDIR
        .hwndOwner = 0&
        .nMaxFile = 65535
        .lpstrInitialDir = ""
        .lpstrFilter = "Arquivos CAD (dgn, dwg, dxf)" & Chr(0) & "*.dgn;*.dwg;*.dxf" & Chr(0) & Chr(0)
        .lpstrFile = Space(.nMaxFile - 1) & Chr(0)
        .lStructSize = Len(tOPENFILENAME)
    End With
    
    lResult = GetOpenFileName(tOPENFILENAME)
    
    If lResult > 0 Then
        With tOPENFILENAME
            vFiles = Split(Left(.lpstrFile, InStr(.lpstrFile, Chr(0) & Chr(0)) - 1), Chr(0))
        End With
        If UBound(vFiles) = 0 Then
            l_arquivos.AddItem
            l_arquivos.List(l_arquivos.ListCount - 1, 0) = vFiles(0)
            
        Else
            For lIndex = 1 To UBound(vFiles)
                l_arquivos.AddItem
                l_arquivos.List(l_arquivos.ListCount - 1, 0) = AddBS(vFiles(0)) & vFiles(lIndex)
            Next
        End If
        'extrai o caminho e atualiza a variavel
        'dir_arqs = Left(l_arquivos.List(l_arquivos.ListCount - 1, 1), InStrRev(l_arquivos.List(l_arquivos.ListCount - 1, 1), "\"))
    End If

End Sub

Private Sub b_limpa_Click()
    If MsgBox("Tem certeza?", vbYesNo, "Limpar a lista existente") = vbYes Then
        CadInputQueue.SendCommand "MODELHISTORY PURGE"
    End If
End Sub

Attribute VB_Name = "verifica_arq"
Declare Function mdlFile_validDesignFile Lib "stdmdlbltin.dll" ( _
    ByRef pThreeD As Long, _
    ByRef pFormat As Long, _
    ByRef pMajorVersion As Long, _
    ByRef pMinorVersion As Long, _
    ByRef ppThumbnail As Long, _
    ByRef pThumbnailSize As Long, _
    ByVal pFileName As String) As Long
 ' ---------------------------------------------------------------------
'   Main
'   Main entry point.  Provide a file name with the MicroStation keyin
'   when calling this module.  For example:
'   vba run CheckFile.Main C:\projects\project1\dgn\myfile.dgn
' ---------------------------------------------------------------------
Public Function ver_formato(ByVal fileName As String) As Boolean
     Dim threeD          As Long, _
        format          As Long, _
        major           As Long, _
        minor           As Long
    ver_formato = False

    If (0 <> mdlFile_validDesignFile(threeD, format, major, minor, 0, 0, fileName)) Then
        Dim dimension   As String
        If (threeD) Then
            dimension = "3D"
        Else
            dimension = "2D"
        End If
        
        Select Case format
        Case msdDesignFileFormatV7
            'MsgBox "'" & fileName & "' is a " & dimension & " V7 DGN file"
            ver_formato = True
        Case msdDesignFileFormatV8
            'MsgBox "'" & fileName & "' is a " & dimension & " V8 DGN file"
            ver_formato = True
        Case msdDesignFileFormatDWG
            'MsgBox "'" & fileName & "' is a DWG file"
            ver_formato = True
        Case msdDesignFileFormatDXF
            'MsgBox "'" & fileName & "' is a DXF file"
            ver_formato = True
        End Select
    Else
        ver_formato = False
    End If
End Function
