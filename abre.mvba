Attribute VB_Name = "Form_abre_lista"
Attribute VB_Base = "0{E416D778-97DF-4C5A-B95A-C507DD0B7483}{8F8B09CB-BA39-4C69-AB62-B917C422E972}"
Attribute VB_GlobalNameSpace = False
Attribute VB_Creatable = False
Attribute VB_PredeclaredId = True
Attribute VB_Exposed = False
Attribute VB_TemplateDerived = False
Attribute VB_Customizable = False
Private Sub B_abre_Click()
    'habilitar o TreeView em tools->references e marcar "Microsoft Windows Common Controls 6.0 (SP6)"
    
    Dim num_des As Integer
    num_des = 0
    
    'varre a lista de visualização
    For i = 1 To TreeView1.Nodes.Count
        nome_arq = TreeView1.Nodes(i).Text 'pega o caminho completo do arquivo
        
        If verifica_arq.ver_formato(nome_arq) Then 'verifica se um arquivo CAD
            OpenDesignFile nome_arq, False, msdV7ActionUpgradeToV8 'abre o arquivo
            num_des = num_des + 1
        End If
        
    Next i
    
    'volta para o inicio da lista
    For i = 1 To num_des
        CadInputQueue.SendCommand "MODELHISTORY BACK"
    Next i
    
    MsgBox "Pronto! Desenhos abertos=" & num_des
    
End Sub

Private Sub b_limpa_Click()
    If MsgBox("Tem certeza?", vbYesNo, "Limpar a lista existente") = vbYes Then
        CadInputQueue.SendCommand "MODELHISTORY PURGE"
    End If
        
End Sub

Private Sub TreeView1_OLEDragDrop(Data As MSComctlLib.DataObject, Effect As Long, Button As Integer, Shift As Integer, x As Single, y As Single)
    'habilitar o TreeView em tools->references e marcar "Microsoft Windows Common Controls 6.0 (SP6)"
    
    ' varre o objeto gerado pelo "drag'n drop"
    For i = 1 To Data.Files.Count
        StrPath = Data.Files(i) 'pega cada arquivo e
        TreeView1.Nodes.Add , , , StrPath 'adiciona a lista de visualização
        
    Next i
        
End Sub

Attribute VB_Name = "abre_lista"
Sub executa()
    
    Load Form_abre_lista
    Form_abre_lista.Show 0
End Sub

Attribute VB_Name = "verifica_arq"
Declare Function mdlFile_validDesignFile Lib "stdmdlbltin.dll" ( _
    ByRef pThreeD As Long, _
    ByRef pFormat As Long, _
    ByRef pMajorVersion As Long, _
    ByRef pMinorVersion As Long, _
    ByRef ppThumbnail As Long, _
    ByRef pThumbnailSize As Long, _
    ByVal pFileName As String) As Long

Public Function ver_formato(ByVal fileName As String) As Boolean
     Dim threeD          As Long, _
        format          As Long, _
        major           As Long, _
        minor           As Long
    ver_formato = False

    If (0 <> mdlFile_validDesignFile(threeD, format, major, minor, 0, 0, fileName)) Then
        Dim dimension   As String
        If (threeD) Then
            dimension = "3D"
        Else
            dimension = "2D"
        End If
        
        Select Case format
        Case msdDesignFileFormatV7
            'MsgBox "'" & fileName & "' is a " & dimension & " V7 DGN file"
            ver_formato = True
        Case msdDesignFileFormatV8
            'MsgBox "'" & fileName & "' is a " & dimension & " V8 DGN file"
            ver_formato = True
        Case msdDesignFileFormatDWG
            'MsgBox "'" & fileName & "' is a DWG file"
            ver_formato = True
        Case msdDesignFileFormatDXF
            'MsgBox "'" & fileName & "' is a DXF file"
            ver_formato = True
        End Select
    Else
        ver_formato = False
    End If
End Function
