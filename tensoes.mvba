Attribute VB_Name = "cls_tensoes"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Public formulario As form_tensoes
Public compr_ini As Double

Private m_atPoints(0 To 1) As Point3d
Private m_nPoints As Integer

Private Sub IPrimitiveCommandEvents_Cleanup()

End Sub

Private Sub IPrimitiveCommandEvents_DataPoint(Point As Point3d, ByVal View As View)

    If m_nPoints = 0 Then
        CommandState.StartDynamics
        m_atPoints(0) = Point
        ShowPrompt "Entre a ancoragem 2"
        m_nPoints = 1
    ElseIf m_nPoints = 1 Then
        m_atPoints(1) = Point
        
        
        ShowPrompt "Confirme os valores"
        m_nPoints = 2
        
    ElseIf m_nPoints = 2 Then
        Dim flecha As Double
        Dim h As Double
        Dim v As Double
        Dim tensao As Double
        Dim compr As Double
        Dim temp_ant As Double
        Dim conjunto As CellElement
        
        'obtem os parametros iniciais - comprimento, dist horizontal e vertical
        Set conjunto = cat_isol(m_atPoints(0), m_atPoints(1), _
            CDbl(formulario.e_tensao.Value), CDbl(formulario.e_peso.Value), _
            CDbl(formulario.e_peso_isol.Value), CDbl(formulario.e_compr_isol.Value), _
            compr, flecha, h, v)
        
        ' parametros de varredura da temperatura
        temp_ini = CInt(formulario.e_temp_ini.Value)
        temp_final = CInt(formulario.e_temp_final.Value)
        temp_passo = CInt(formulario.e_temp_passo.Value)
        
        If temp_passo = 0 Then
            temp_passo = 1
        End If
        
        formulario.e_result.Text = ""
        
        'cabeçalho da tabela de resultados
        formulario.e_result.Text = formulario.e_result.Text & _
                "Temp" & vbTab & _
                "Tensao" & vbTab & _
                "Flecha" & vbNewLine
        
        compr_ini = compr
        tensao_ant = CDbl(formulario.e_tensao.Value)
        
        E = CDbl(formulario.e_elas.Value)
        S = CDbl(formulario.e_secao.Value)
        
        compr0 = compr / ((tensao_ant * 9.8) / (E * S) + 1)
        'Debug.Print " L=" & CStr(compr) & " L0=" & CStr(compr0)
        
        'inicia a varredura da temperatura
        temp_ant = temp_ini
        For temp = temp_ini To temp_final Step temp_passo
            'calcula o novo comprimento considerando a dilatação linear
            compr = compr * (1 + CDbl(formulario.e_dilata.Value) * (temp - temp_ant))
            
            compr_esp = compr0 * (1 + CDbl(formulario.e_dilata.Value) * (temp - temp_ini))
            
            'obtem a tensão correspondente
            tensao_a = compr_tensao(compr, Abs(h), Abs(v), CDbl(formulario.e_peso.Value))
            tensao_b = tensao_ant
            
            'Debug.Print " t=" & CStr(temp)
            For i = 0 To 20
                tensao = (tensao_a + tensao_b) / 2
                compr_esp = compr0 * (1 + CDbl(formulario.e_dilata.Value) * (temp - temp_ini))
                compr_esp = compr_esp * ((tensao * 9.8) / (E * S) + 1)
                Set a = cat_isol(m_atPoints(0), m_atPoints(1), _
                    tensao, CDbl(formulario.e_peso.Value), _
                    CDbl(formulario.e_peso_isol.Value), CDbl(formulario.e_compr_isol.Value), _
                    compr, flecha, h, v)
                If Abs((compr_esp - compr) / compr_esp) < 0.0000001 Then
                    Exit For
                ElseIf (compr_esp - compr) < 0 Then
                    tensao_a = tensao
                Else
                    tensao_b = tensao
                End If
                'Debug.Print CStr(i) & " erro=" & CStr(100 * (compr_esp - compr))
                
            Next i
            
            
            'resolve a catenária com isoladores e já desenha
            a = adiciona_cj(m_atPoints(0), m_atPoints(1), _
                tensao, CDbl(formulario.e_peso.Value), _
                CDbl(formulario.e_peso_isol.Value), CDbl(formulario.e_compr_isol.Value), _
                CDbl(temp), compr, flecha, h, v)
            'exibe o resultado na tabela
            formulario.e_result.Text = formulario.e_result.Text & _
                CStr(temp) & vbTab & _
                Format(tensao, "###0.000") & vbTab & _
                Format(flecha, "###0.000") & vbNewLine
            temp_ant = temp
            tensao_ant = tensao
        Next temp
        
        formulario.e_result.SelStart = 0
        formulario.e_result.SelLength = formulario.e_result.TextLength
        formulario.e_result.Copy
        
        
        m_nPoints = 0
        CommandState.StartDefaultCommand
    End If
    
End Sub


Private Sub IPrimitiveCommandEvents_Dynamics(Point As Point3d, ByVal View As View, ByVal DrawMode As MsdDrawingMode)
    If m_nPoints = 1 Then
        m_atPoints(1) = Point
    End If
        
    If m_nPoints > 0 Then
        Dim compr As Double
        Dim flecha As Double
        Dim h As Double
        Dim v As Double
        
        Dim conjunto As CellElement
        Set conjunto = cat_isol(m_atPoints(0), m_atPoints(1), _
            CDbl(formulario.e_tensao.Value), CDbl(formulario.e_peso.Value), _
            CDbl(formulario.e_peso_isol.Value), CDbl(formulario.e_compr_isol.Value), _
            compr, flecha, h, v)
        conjunto.Redraw DrawMode
        
        formulario.l_compr.Caption = CStr(compr)
        formulario.l_flecha.Caption = CStr(flecha)
        
    End If
End Sub

Private Sub IPrimitiveCommandEvents_Keyin(ByVal Keyin As String)

End Sub

Private Sub IPrimitiveCommandEvents_Reset()
    'CommandState.StartPrimitive Me
    m_nPoints = 0
    CommandState.StartDefaultCommand
End Sub

Private Sub IPrimitiveCommandEvents_Start()
    ShowCommand "Desenha catenaria"
    ShowPrompt "Entre a ancoragem 1"
End Sub

Attribute VB_Name = "form_tensoes"
Attribute VB_Base = "0{593BDDF5-85A6-43FC-8D98-D6F5AB761880}{2F1D18F6-FC9B-4DEF-90AE-DC55339BC0E1}"
Attribute VB_GlobalNameSpace = False
Attribute VB_Creatable = False
Attribute VB_PredeclaredId = True
Attribute VB_Exposed = False
Attribute VB_TemplateDerived = False
Attribute VB_Customizable = False
Public tensoes_cls As cls_tensoes


Private Sub b_inicio_Click()
    CommandState.StartPrimitive tensoes_cls
    CommandState.EnableAccuSnap
End Sub


Private Sub c_cabo_Change()
    tipo_i = c_tipo_cabo.ListIndex
    
    cabos = dados_caa()
    
    If tipo_i = 0 Then
        cabos = dados_ca()
    ElseIf tipo_i = 1 Then
        cabos = dados_caa()
    ElseIf tipo_i = 2 Then
        cabos = dados_caal()
    ElseIf tipo_i = 3 Then
        cabos = dados_aco()
    End If
    
    indice = c_cabo.ListIndex
    If indice > -1 Then
        cabo = cabos(indice)
        e_peso.Value = CStr(cabo(2))
        e_dilata.Value = CStr(cabo(4))
        e_secao.Value = CStr(cabo(1))
        e_elas.Value = CStr(cabo(3))
    End If
    
    
End Sub

Private Sub c_tipo_cabo_Change()
    tipo_i = c_tipo_cabo.ListIndex
    
    cabos = dados_caa()
    
    c_cabo.Clear
    
    If tipo_i = 0 Then
        cabos = ""
        cabos = dados_ca()
    ElseIf tipo_i = 1 Then
        cabos = ""
        cabos = dados_caa()
    ElseIf tipo_i = 2 Then
        cabos = ""
        cabos = dados_caal()
    ElseIf tipo_i = 3 Then
        cabos = ""
        cabos = dados_aco()
    End If
    For Each cabo In cabos
        c_cabo.AddItem (cabo(0))
    Next

End Sub


Private Sub UserForm_Initialize()
    cabos_caa = dados_caa()
    
    c_tipo_cabo.AddItem ("Aluminio (CA)")
    c_tipo_cabo.AddItem ("Alma aço (CAA)")
    c_tipo_cabo.AddItem ("Liga (CAAL)")
    c_tipo_cabo.AddItem ("Aço (HS)")
    
    
    For Each cabo In cabos_caa
        c_cabo.AddItem (cabo(0))
    Next
    
End Sub

Attribute VB_Name = "m_tensoes"
'Hyperbolic Sine HSin(X) = (Exp(X) – Exp(-X)) / 2
Function sinh(X)
    sinh = (Exp(X) - Exp(-X)) / 2
End Function

'Hyperbolic Cosine HCos(X) = (Exp(X) + Exp(-X)) / 2
Function cosh(X)
    cosh = (Exp(X) + Exp(-X)) / 2
End Function

'HArctan(X) = Log((1 + X) / (1 – X)) / 2
Function atanh(X)
    atanh = Log((1 + X) / (1 - X)) / 2
End Function

Function ArcTan2(X, Y)

    'Const PI As Double = 3.14159265358979
    Const PI_2 As Double = 1.5707963267949

    Select Case X
        Case Is > 0
            ArcTan2 = Atn(Y / X)
        Case Is < 0
            ArcTan2 = Atn(Y / X) + PI * Sgn(Y)
            If Y = 0 Then ArcTan2 = ArcTan2 + PI
        Case Is = 0
            ArcTan2 = PI_2 * Sgn(Y)
    End Select

End Function

Function catenaria(inicio As Point3d, final As Point3d, tensao As Double, peso As Double) As Point3d()
    Dim points(0 To 20) As Point3d
    Dim t As Integer
    
    'calcula o parametro da catenaria
    a = Abs(1000 * tensao / peso)
    
    'a partir dos pontos de entrada, obtem delta x e delta y
    dx = Abs(final.X - inicio.X)
    dy = final.Y - inicio.Y
    
    'sentido do eixo x, para plotegem correta da curva
    sinal = Sgn(final.X - inicio.X)
    
    'calcula o comprimento da corda
    S = Sqr((2 * a * sinh(dx / (2 * a))) ^ 2 + dy ^ 2)
    
    x0 = -atanh(dy / S) * a 'deslocamento horizontal do ponto mínimo
    
    Step = dx / 20
    umin = -dx / 2
    umax = dx / 2
    y0 = a * cosh((umin - x0) / a) 'deslocamento vertical
    
    u = umin
    'calcula os pontos da curva
    For t = 0 To 20
       points(t).X = sinal * (u - umin) + inicio.X
       points(t).Y = a * cosh((u - x0) / a) - y0 + inicio.Y
       u = u + Step
    Next t
    
    'retorna a lista de pontos
    catenaria = points
End Function

Function catenaria2(inicio As Point3d, final As Point3d, tensao As Double, peso As Double, ByRef compr As Double, ByRef flecha As Double) As Point3d()
    Dim points(0 To 20) As Point3d
    Dim t As Integer
    
    'calcula o parametro da catenaria
    a = Abs(1000 * tensao / peso)
    
    'a partir dos pontos de entrada, obtem delta x e delta y
    dx = Abs(final.X - inicio.X)
    dy = final.Y - inicio.Y
    
    'sentido do eixo x, para plotegem correta da curva
    sinal = Sgn(final.X - inicio.X)
    
    'calcula o comprimento da corda
    S = Sqr((2 * a * sinh(dx / (2 * a))) ^ 2 + dy ^ 2)
    
    x0 = -atanh(dy / S) * a 'deslocamento horizontal do ponto mínimo
    
    Step = dx / 20
    umin = -dx / 2
    umax = dx / 2
    y0 = a * cosh((umin - x0) / a) 'deslocamento vertical
    
    u = umin
    'calcula os pontos da curva
    For t = 0 To 20
       points(t).X = sinal * (u - umin) + inicio.X
       points(t).Y = a * cosh((u - x0) / a) - y0 + inicio.Y
       u = u + Step
    Next t
    
    'retorna os valores
    compr = S
    flecha = a * cosh((-x0) / a) - y0
    catenaria2 = points
End Function

Function cat_tagset() As TagSet
    Dim strName As String
    Dim oTagSets As TagSets
    
    strName = "dados_catenaria"
    Set oTagSets = ActiveDesignFile.TagSets
    On Error Resume Next
    Set cat_tagset = oTagSets(strName)
    If cat_tagset Is Nothing Then
        Dim td As TagDefinition
        Set cat_tagset = oTagSets.Add(strName)
        Set td = cat_tagset.TagDefinitions.Add("tensao", msdTagTypeDouble)
        td.IsConstant = False
        td.IsHidden = True
        Set td = cat_tagset.TagDefinitions.Add("flecha", msdTagTypeDouble)
        td.IsConstant = False
        td.IsHidden = True
        Set td = cat_tagset.TagDefinitions.Add("compr", msdTagTypeDouble)
        td.IsConstant = False
        td.IsHidden = True
        Set td = cat_tagset.TagDefinitions.Add("temperatura", msdTagTypeDouble)
        td.IsConstant = False
        td.IsHidden = True
        Set td = cat_tagset.TagDefinitions.Add("peso_prop", msdTagTypeDouble)
        td.IsConstant = False
        td.IsHidden = True
        Set td = cat_tagset.TagDefinitions.Add("peso_isol", msdTagTypeDouble)
        td.IsConstant = False
        td.IsHidden = True
        Set td = cat_tagset.TagDefinitions.Add("compr_isol", msdTagTypeDouble)
        td.IsConstant = False
        td.IsHidden = True
        Set td = cat_tagset.TagDefinitions.Add("anc1_x", msdTagTypeDouble)
        td.IsConstant = False
        td.IsHidden = True
        Set td = cat_tagset.TagDefinitions.Add("anc1_y", msdTagTypeDouble)
        td.IsConstant = False
        td.IsHidden = True
        Set td = cat_tagset.TagDefinitions.Add("anc2_x", msdTagTypeDouble)
        td.IsConstant = False
        td.IsHidden = True
        Set td = cat_tagset.TagDefinitions.Add("anc2_y", msdTagTypeDouble)
        td.IsConstant = False
        td.IsHidden = True
        Set td = cat_tagset.TagDefinitions.Add("id_cabo", msdTagTypeCharacter)
        td.IsConstant = False
        td.IsHidden = True
        Set td = cat_tagset.TagDefinitions.Add("id_isol", msdTagTypeCharacter)
        td.IsConstant = False
        td.IsHidden = True
    End If
End Function


Function cat_isol(inicio As Point3d, final As Point3d, _
    tensao As Double, peso As Double, peso_isol As Double, compr_isol As Double, _
    ByRef compr As Double, ByRef flecha As Double, _
    ByRef h As Double, ByRef v As Double) As CellElement
    
    Dim points() As Point3d
    Dim isolador(1) As Point3d
    Dim ele(0 To 2) As Element
    Dim des_isol(5) As Point3d
    
    'primeira catenaria, sem isolador, para estimar os angulos da tensão aplicada
    points = catenaria(inicio, final, tensao, peso)
    
    'calcula o angulo da tensao no primeiro isolador
    dx = points(1).X - points(0).X
    dy = points(1).Y - points(0).Y
    ang = ArcTan2(dx, dy)
    'calcula o angulo de rotação do primeiro isolador
    tx = tensao * Cos(ang)
    ty = tensao * Sin(ang) - peso_isol
    ang = ArcTan2(tx, ty)
    'calcula o novo ponto de ancoragem da catenaria
    isolador(0) = inicio
    isolador(0).X = isolador(0).X + compr_isol * Cos(ang)
    isolador(0).Y = isolador(0).Y + compr_isol * Sin(ang)
    
    'desenho do primeiro isolador
    des_isol(0) = inicio
    des_isol(1).X = inicio.X + (0.1 * Cos(ang) - 0.1 * Sin(ang))
    des_isol(1).Y = inicio.Y + 0.1 * Sin(ang) + 0.1 * Cos(ang)
    des_isol(2).X = inicio.X + ((compr_isol - 0.1) * Cos(ang) - 0.1 * Sin(ang))
    des_isol(2).Y = inicio.Y + (compr_isol - 0.1) * Sin(ang) + 0.1 * Cos(ang)
    des_isol(3) = isolador(0)
    des_isol(4).X = inicio.X + ((compr_isol - 0.1) * Cos(ang) + 0.1 * Sin(ang))
    des_isol(4).Y = inicio.Y + (compr_isol - 0.1) * Sin(ang) - 0.1 * Cos(ang)
    des_isol(5).X = inicio.X + (0.1 * Cos(ang) + 0.1 * Sin(ang))
    des_isol(5).Y = inicio.Y + 0.1 * Sin(ang) - 0.1 * Cos(ang)
    Set ele(0) = CreateShapeElement1(Nothing, des_isol)

    'calcula o angulo da tensao no segundo isolador
    dx = points(19).X - points(20).X
    dy = points(19).Y - points(20).Y
    ang = ArcTan2(dx, dy)
    'calcula o angulo de rotação do segundo isolador
    tx = tensao * Cos(ang)
    ty = tensao * Sin(ang) - peso_isol
    ang = ArcTan2(tx, ty)
    'calcula o novo ponto de ancoragem da catenaria
    isolador(1) = final
    isolador(1).X = isolador(1).X + compr_isol * Cos(ang)
    isolador(1).Y = isolador(1).Y + compr_isol * Sin(ang)
    
    'desenho do segundo isolador
    des_isol(0) = final
    des_isol(1).X = final.X + (0.1 * Cos(ang) - 0.1 * Sin(ang))
    des_isol(1).Y = final.Y + 0.1 * Sin(ang) + 0.1 * Cos(ang)
    des_isol(2).X = final.X + ((compr_isol - 0.1) * Cos(ang) - 0.1 * Sin(ang))
    des_isol(2).Y = final.Y + (compr_isol - 0.1) * Sin(ang) + 0.1 * Cos(ang)
    des_isol(3) = isolador(1)
    des_isol(4).X = final.X + ((compr_isol - 0.1) * Cos(ang) + 0.1 * Sin(ang))
    des_isol(4).Y = final.Y + (compr_isol - 0.1) * Sin(ang) - 0.1 * Cos(ang)
    des_isol(5).X = final.X + (0.1 * Cos(ang) + 0.1 * Sin(ang))
    des_isol(5).Y = final.Y + 0.1 * Sin(ang) - 0.1 * Cos(ang)
    Set ele(1) = CreateShapeElement1(Nothing, des_isol)
    
    'segunda catenaria, considerando os isoladores
    points = catenaria2(isolador(0), isolador(1), tensao, peso, compr, flecha)
    
    'corrige o valor da flecha, considerando o isolador
    flecha = (final.Y - inicio.Y) / 2 - (flecha + isolador(0).Y - inicio.Y)
    
    h = isolador(1).X - isolador(0).X
    v = isolador(1).Y - isolador(0).Y
    
    Set ele(2) = CreateLineElement1(Nothing, points)
    
    'Set ele(3) = CreateTextElement1(Nothing, "T=" & CStr(tensao), inicio, Matrix3dIdentity)
    
    'retorna o desenho do conjunto
    Set cat_isol = CreateCellElement1(vbNullString, ele, inicio, False)
    
    
End Function

Function adiciona_cj(inicio As Point3d, final As Point3d, _
    tensao As Double, peso As Double, peso_isol As Double, compr_isol As Double, _
    temperatura As Double, _
    ByRef compr As Double, ByRef flecha As Double, _
    ByRef h As Double, ByRef v As Double)
    
    'cria o desenho do conjunto cabo/isoladores
    Dim conjunto As CellElement
    Set conjunto = cat_isol(inicio, final, _
        tensao, peso, _
        peso_isol, compr_isol, _
        compr, flecha, h, v)
    ActiveModelReference.AddElement conjunto
    
'    'adiciona as etiquetas de marcação
'    Dim ts As TagSet
'    Dim eleTag As TagElement
'    Dim tagDef As TagDefinition
'    Dim tagDefs As TagDefinitions
'
'    Set ts = cat_tagset 'pega ou cria a tagset
'    'adiciona as etiquetas
'    Set tagDefs = ts.TagDefinitions
'    Set tagDef = tagDefs("tensao")
'    Set eleTag = conjunto.AddTag(tagDef)
'    eleTag.Value = tensao
'    eleTag.Redraw
'    eleTag.Rewrite
'
'    Set tagDef = tagDefs("compr")
'    Set eleTag = conjunto.AddTag(tagDef)
'    eleTag.Value = compr
'    eleTag.Redraw
'    eleTag.Rewrite
'
'    Set tagDef = tagDefs("flecha")
'    Set eleTag = conjunto.AddTag(tagDef)
'    eleTag.Value = flecha
'    eleTag.Redraw
'    eleTag.Rewrite
'
'    Set tagDef = tagDefs("temperatura")
'    Set eleTag = conjunto.AddTag(tagDef)
'    eleTag.Value = temperatura
'    eleTag.Redraw
'    eleTag.Rewrite
'
'    Set tagDef = tagDefs("id_isol")
'    Set eleTag = conjunto.AddTag(tagDef)
'    eleTag.Value = "Vidro 138kV"
'    eleTag.Redraw
'    eleTag.Rewrite
'
'    Set tagDef = tagDefs("peso_prop")
'    Set eleTag = conjunto.AddTag(tagDef)
'    eleTag.Value = peso
'    eleTag.Redraw
'    eleTag.Rewrite
'
'    Set tagDef = tagDefs("peso_isol")
'    Set eleTag = conjunto.AddTag(tagDef)
'    eleTag.Value = peso_isol
'    eleTag.Redraw
'    eleTag.Rewrite
'
'    Set tagDef = tagDefs("compr_isol")
'    Set eleTag = conjunto.AddTag(tagDef)
'    eleTag.Value = compr_isol
'    eleTag.Redraw
'    eleTag.Rewrite
'
'    Set tagDef = tagDefs("anc1_x")
'    Set eleTag = conjunto.AddTag(tagDef)
'    eleTag.Value = inicio.X
'    eleTag.Redraw
'    eleTag.Rewrite
'
'    Set tagDef = tagDefs("anc1_y")
'    Set eleTag = conjunto.AddTag(tagDef)
'    eleTag.Value = inicio.Y
'    eleTag.Redraw
'    eleTag.Rewrite
'
'    Set tagDef = tagDefs("anc2_x")
'    Set eleTag = conjunto.AddTag(tagDef)
'    eleTag.Value = final.X
'    eleTag.Redraw
'    eleTag.Rewrite
'
'    Set tagDef = tagDefs("anc2_y")
'    Set eleTag = conjunto.AddTag(tagDef)
'    eleTag.Value = final.Y
'    eleTag.Redraw
'    eleTag.Rewrite

    Dim Xdata() As XDatum
    AppendXDatum Xdata, msdXDatumTypeControlString, "{"
    AppendXDatum Xdata, msdXDatumTypeString, "ancoragem1"
    AppendXDatum Xdata, msdXDatumTypePoint, inicio
    AppendXDatum Xdata, msdXDatumTypeString, "ancoragem2"
    AppendXDatum Xdata, msdXDatumTypePoint, final
    AppendXDatum Xdata, msdXDatumTypeString, "tensao"
    AppendXDatum Xdata, msdXDatumTypeReal, tensao
    AppendXDatum Xdata, msdXDatumTypeString, "peso_prop"
    AppendXDatum Xdata, msdXDatumTypeReal, peso
    AppendXDatum Xdata, msdXDatumTypeString, "peso_isol"
    AppendXDatum Xdata, msdXDatumTypeReal, peso_isol
    AppendXDatum Xdata, msdXDatumTypeString, "comp_isol"
    AppendXDatum Xdata, msdXDatumTypeReal, compr_isol
    AppendXDatum Xdata, msdXDatumTypeString, "temperatura"
    AppendXDatum Xdata, msdXDatumTypeReal, temperatura
    AppendXDatum Xdata, msdXDatumTypeString, "compr_cabo"
    AppendXDatum Xdata, msdXDatumTypeReal, compr
    AppendXDatum Xdata, msdXDatumTypeString, "flecha"
    AppendXDatum Xdata, msdXDatumTypeReal, flecha
    AppendXDatum Xdata, msdXDatumTypeControlString, "}"
    conjunto.SetXData "tensoes_flechas", Xdata
    
    conjunto.Rewrite
    conjunto.Redraw
    
    
    
End Function

Function compr_tensao(compr, dx, dy, peso)
    ' retorna a tensão aplicada em função do comprimento do cabo
    
    'valor inicial de a (chute)
    a = dx / ((Log(compr / ((dx ^ 2 + dy ^ 2) ^ 0.5))) ^ 0.5) / 5
    
    prev_a = 0
    
    'metodo iterativo de Newton - Raphson
    For i = 0 To 100 'máximo de 100 iterações
        prev_a = a
        
        ' xn = x - f(x)/f'(x)
        a = a - ((2 * a * sinh(dx / (2 * a)) - (compr ^ 2 - dy ^ 2) ^ 0.5) ^ 2) / (2 * (2 * sinh(dx / (2 * a)) - (dx * cosh(dx / (2 * a))) / a) * (2 * a * sinh(dx / (2 * a)) - (compr ^ 2 - dy ^ 2) ^ 0.5))
        
        If Abs(prev_a - a) / a < 0.00001 Then ' critério de parada - sai do loop se o erro for menor que 0.001%
            Exit For
        End If
    Next i
    
    'Debug.Print "passos=" & CStr(i)
    
    'calcula a tensão, em razao do parametro a da catenaria
    compr_tensao = a * peso / 1000
    
End Function

Function dados_caa()
    Dim cabos_caa(44)
    cabos_caa(0) = Array("Wren", 9.77, 33.9, 79000, 0.0000191)
    cabos_caa(1) = Array("Warbler", 12.32, 42.7, 79000, 0.0000191)
    cabos_caa(2) = Array("Turkey", 15.52, 53.7, 79000, 0.0000191)
    cabos_caa(3) = Array("Thrush", 19.57, 67.8, 79000, 0.0000191)
    cabos_caa(4) = Array("Swan", 24.71, 85.6, 79000, 0.0000191)
    cabos_caa(5) = Array("Swallow", 31.12, 107.8, 79000, 0.0000191)
    cabos_caa(6) = Array("Sparrow", 39.19, 135.8, 79000, 0.0000191)
    cabos_caa(7) = Array("Robin", 49.48, 171.4, 79000, 0.0000191)
    cabos_caa(8) = Array("Raven", 62.44, 216.2, 79000, 0.0000191)
    cabos_caa(9) = Array("Quail", 78.55, 272, 79000, 0.0000191)
    cabos_caa(10) = Array("Pigeon", 99.3, 343.8, 79000, 0.0000191)
    cabos_caa(11) = Array("Penguin", 125.1, 433.4, 79000, 0.0000191)
    cabos_caa(12) = Array("Waxwing", 142.5, 430.6, 68000, 0.0000212)
    cabos_caa(13) = Array("Partridge", 156.9, 545.6, 74000, 0.0000189)
    cabos_caa(14) = Array("Ostrich", 176.7, 614.4, 74000, 0.0000189)
    cabos_caa(15) = Array("Piper", 187.5, 699.5, 78000, 0.0000178)
    cabos_caa(16) = Array("Merlin", 179.7, 543.2, 68000, 0.0000212)
    cabos_caa(17) = Array("Linnet", 198.4, 689.8, 74000, 0.0000189)
    cabos_caa(18) = Array("Oriole", 210.3, 784.7, 78000, 0.0000178)
    cabos_caa(19) = Array("Chickadee", 212.1, 641, 68000, 0.0000212)
    cabos_caa(20) = Array("Ibis", 234.1, 813.9, 74000, 0.0000189)
    cabos_caa(21) = Array("Lark", 247.8, 924.7, 78000, 0.0000178)
    cabos_caa(22) = Array("Pelican", 255.8, 773, 68000, 0.0000212)
    cabos_caa(23) = Array("Hawk", 281.1, 977.9, 74000, 0.0000189)
    cabos_caa(24) = Array("Hen", 297.6, 1110.4, 78000, 0.0000178)
    cabos_caa(25) = Array("Heron", 312.5, 1165.8, 78000, 0.0000178)
    cabos_caa(26) = Array("Osprey", 298.2, 901, 68000, 0.0000212)
    cabos_caa(27) = Array("Dove", 328.5, 1141.5, 74000, 0.0000189)
    cabos_caa(28) = Array("Eagle", 347.9, 1298, 78000, 0.0000178)
    cabos_caa(29) = Array("Duck", 346.3, 1159.5, 67000, 0.0000194)
    cabos_caa(30) = Array("Squab", 355.6, 1236.2, 74000, 0.0000189)
    cabos_caa(31) = Array("King Bird", 340.9, 1029.8, 68000, 0.0000212)
    cabos_caa(32) = Array("Grosbeak", 374.3, 1301.7, 74000, 0.0000189)
    cabos_caa(33) = Array("Egret", 396.1, 1471.3, 75000, 0.000018)
    cabos_caa(34) = Array("Gannet", 393.2, 1366.1, 74000, 0.0000189)
    cabos_caa(35) = Array("Starlin", 421, 1465, 74000, 0.0000189)
    cabos_caa(36) = Array("Drake", 468, 1626, 74000, 0.0000189)
    cabos_caa(37) = Array("Mallard", 495.6, 1840, 75000, 0.000018)
    cabos_caa(38) = Array("Ruddy", 487.2, 1510, 65000, 0.0000209)
    cabos_caa(39) = Array("Canary", 515.3, 1752, 67000, 0.0000194)
    cabos_caa(40) = Array("Rail", 517.4, 1603, 65000, 0.0000209)
    cabos_caa(41) = Array("Cardinal", 547.3, 1832, 67000, 0.0000194)
    cabos_caa(42) = Array("Ortolan", 560.2, 1735, 65000, 0.0000209)
    cabos_caa(43) = Array("Curlew", 590.2, 1976, 67000, 0.0000194)
    cabos_caa(44) = Array("Bluejay", 604.4, 1871, 65000, 0.0000209)
    
    dados_caa = cabos_caa
    
End Function

Function dados_caal()
    Dim cabos_caal(155)
    cabos_caal(0) = Array("Adamantina", 15.49, 42.7, 60000, 0.000023)
    cabos_caal(1) = Array("Alagoinha", 21.15, 58.2, 60000, 0.000023)
    cabos_caal(2) = Array("Alcântara", 24.67, 68, 60000, 0.000023)
    cabos_caal(3) = Array("Alcobaça", 33.62, 92.5, 60000, 0.000023)
    cabos_caal(4) = Array("Alegrete", 39.25, 108.2, 60000, 0.000023)
    cabos_caal(5) = Array("Americana", 53.52, 147.6, 60000, 0.000023)
    cabos_caal(6) = Array("Amparo", 62.47, 172.2, 60000, 0.000023)
    cabos_caal(7) = Array("Anápolis", 67.44, 185.7, 60000, 0.000023)
    cabos_caal(8) = Array("Anchieta", 78.74, 217.1, 60000, 0.000023)
    cabos_caal(9) = Array("Aparecida", 85.02, 234.1, 60000, 0.000023)
    cabos_caal(10) = Array("Apucarana", 99.16, 273.4, 60000, 0.000023)
    cabos_caal(11) = Array("Aracati", 107.2, 294.7, 60000, 0.000023)
    cabos_caal(12) = Array("Araçatuba", 125.1, 344.9, 60000, 0.000023)
    cabos_caal(13) = Array("Araguaiana", 126.28, 349.3, 60000, 0.000023)
    cabos_caal(14) = Array("Araguari", 126.68, 349.3, 60000, 0.000023)
    cabos_caal(15) = Array("Arapiraca", 152.01, 418.8, 60000, 0.000023)
    cabos_caal(16) = Array("Araranguá", 152.01, 418.8, 60000, 0.000023)
    cabos_caal(17) = Array("Araraquara", 177.34, 489.7, 60000, 0.000023)
    cabos_caal(18) = Array("Andradina", 177.34, 489.7, 60000, 0.000023)
    cabos_caal(19) = Array("Araruama", 202.68, 558.8, 60000, 0.000023)
    cabos_caal(20) = Array("Araxá", 202.68, 558.8, 60000, 0.000023)
    cabos_caal(21) = Array("Arcoverde", 228.02, 628.9, 60000, 0.000023)
    cabos_caal(22) = Array("Aruaná", 228.02, 628.9, 60000, 0.000023)
    cabos_caal(23) = Array("Assis", 253.35, 698.4, 60000, 0.000023)
    cabos_caal(24) = Array("Atrântida", 253.35, 698.4, 60000, 0.000023)
    cabos_caal(25) = Array("Atibaia", 253.35, 698.4, 60000, 0.000023)
    cabos_caal(26) = Array("Avaré", 253.35, 698.4, 60000, 0.000023)
    cabos_caal(27) = Array("Bacabai", 253.35, 698.4, 60000, 0.000023)
    cabos_caal(28) = Array("Bagé", 253.35, 698.4, 60000, 0.000023)
    cabos_caal(29) = Array("Barbacena", 278.69, 768.3, 60000, 0.000023)
    cabos_caal(30) = Array("Barretos", 278.69, 768.3, 60000, 0.000023)
    cabos_caal(31) = Array("Batatis", 278.69, 768.3, 60000, 0.000023)
    cabos_caal(32) = Array("Bauru", 278.69, 768.3, 60000, 0.000023)
    cabos_caal(33) = Array("Bebedouro", 278.69, 768.3, 60000, 0.000023)
    cabos_caal(34) = Array("Bertioga", 278.69, 768.3, 60000, 0.000023)
    cabos_caal(35) = Array("Blumenau", 304.02, 838.1, 60000, 0.000023)
    cabos_caal(36) = Array("Botucatu", 304.02, 838.1, 60000, 0.000023)
    cabos_caal(37) = Array("Bragança", 304.02, 838.1, 60000, 0.000023)
    cabos_caal(38) = Array("Brodósqui", 304.02, 838.1, 60000, 0.000023)
    cabos_caal(39) = Array("Brusque", 304.02, 838.1, 60000, 0.000023)
    cabos_caal(40) = Array("Cabedelo", 304.02, 838.1, 60000, 0.000023)
    cabos_caal(41) = Array("Cabo", 329.35, 908.1, 60000, 0.000023)
    cabos_caal(42) = Array("Caçapava", 329.35, 908.1, 60000, 0.000023)
    cabos_caal(43) = Array("Cachoeira", 329.35, 908.1, 60000, 0.000023)
    cabos_caal(44) = Array("Caeté", 329.35, 908.1, 60000, 0.000023)
    cabos_caal(45) = Array("Caiobá", 354.69, 977.9, 60000, 0.000023)
    cabos_caal(46) = Array("Caidas", 354.69, 977.9, 60000, 0.000023)
    cabos_caal(47) = Array("Camboriú", 354.69, 977.9, 60000, 0.000023)
    cabos_caal(48) = Array("Camocim", 354.69, 977.9, 60000, 0.000023)
    cabos_caal(49) = Array("Campinas", 380.02, 1047.7, 60000, 0.000023)
    cabos_caal(50) = Array("Campos", 380.02, 1047.7, 60000, 0.000023)
    cabos_caal(51) = Array("Cananéia", 380.02, 1047.7, 60000, 0.000023)
    cabos_caal(52) = Array("Canela", 380.02, 1047.7, 60000, 0.000023)
    cabos_caal(53) = Array("Canudos", 405.36, 1117.6, 60000, 0.000023)
    cabos_caal(54) = Array("Caravelas", 405.36, 1117.6, 60000, 0.000023)
    cabos_caal(55) = Array("Cascavel", 405.36, 1117.6, 60000, 0.000023)
    cabos_caal(56) = Array("Calanduva", 405.36, 1117.6, 60000, 0.000023)
    cabos_caal(57) = Array("Caxambu", 430.69, 1187.4, 60000, 0.000023)
    cabos_caal(58) = Array("Caxias", 430.69, 1187.4, 60000, 0.000023)
    cabos_caal(59) = Array("Chui", 430.69, 1187.4, 60000, 0.000023)
    cabos_caal(60) = Array("Corumbá", 430.69, 1187.4, 60000, 0.000023)
    cabos_caal(61) = Array("Cotia", 456.03, 1257.3, 60000, 0.000023)
    cabos_caal(62) = Array("Criciúma", 456.03, 1257.3, 60000, 0.000023)
    cabos_caal(63) = Array("Diamantina", 456.03, 1257.3, 60000, 0.000023)
    cabos_caal(64) = Array("Divinolândia", 456.03, 1257.3, 60000, 0.000023)
    cabos_caal(65) = Array("Dourados", 481.36, 1327.1, 60000, 0.000023)
    cabos_caal(66) = Array("Eldorado", 481.36, 1327.1, 60000, 0.000023)
    cabos_caal(67) = Array("Embu", 481.36, 1327.1, 60000, 0.000023)
    cabos_caal(68) = Array("Franca", 481.36, 1327.1, 60000, 0.000023)
    cabos_caal(69) = Array("Furnas", 506.7, 1397, 60000, 0.000023)
    cabos_caal(70) = Array("Garibaldi", 506.7, 1397, 60000, 0.000023)
    cabos_caal(71) = Array("Gramado", 506.7, 1397, 60000, 0.000023)
    cabos_caal(72) = Array("Guarapari", 506.7, 1397, 60000, 0.000023)
    cabos_caal(73) = Array("Guaratuba", 506.7, 1397, 60000, 0.000023)
    cabos_caal(74) = Array("Guarujá", 506.7, 1397, 60000, 0.000023)
    cabos_caal(75) = Array("Iguape", 506.7, 1397, 60000, 0.000023)
    cabos_caal(76) = Array("Ilha Bela", 506.7, 1397, 60000, 0.000023)
    cabos_caal(77) = Array("Itajaí", 557.37, 1536.7, 60000, 0.000023)
    cabos_caal(78) = Array("Itajubá", 557.37, 1536.7, 60000, 0.000023)
    cabos_caal(79) = Array("Itanhaém", 557.37, 1536.7, 60000, 0.000023)
    cabos_caal(80) = Array("Itararé", 557.37, 1536.7, 60000, 0.000023)
    cabos_caal(81) = Array("Itu", 557.37, 95.9, 60000, 0.000023)
    cabos_caal(82) = Array("Jacarei", 557.37, 1536.7, 60000, 0.000023)
    cabos_caal(83) = Array("Jaú", 557.37, 1536.7, 60000, 0.000023)
    cabos_caal(84) = Array("Joinville", 557.37, 1536.7, 60000, 0.000023)
    cabos_caal(85) = Array("Jundiaí", 608.04, 1676.4, 60000, 0.000023)
    cabos_caal(86) = Array("Laguna", 608.04, 1676.4, 60000, 0.000023)
    cabos_caal(87) = Array("Lages", 608.04, 1676.4, 60000, 0.000023)
    cabos_caal(88) = Array("Limoeiro", 608.04, 1676.4, 60000, 0.000023)
    cabos_caal(89) = Array("Lindóia", 608.04, 1676.4, 60000, 0.000023)
    cabos_caal(90) = Array("Lins", 608.04, 1676.4, 60000, 0.000023)
    cabos_caal(91) = Array("Londrina", 608.04, 1676.4, 60000, 0.000023)
    cabos_caal(92) = Array("Lorena", 608.04, 1676.4, 60000, 0.000023)
    cabos_caal(93) = Array("Maranguape", 633.37, 1746.2, 60000, 0.000023)
    cabos_caal(94) = Array("Marília", 633.37, 1746.2, 60000, 0.000023)
    cabos_caal(95) = Array("Mongaguá", 633.37, 1746.2, 60000, 0.000023)
    cabos_caal(96) = Array("Nazaré", 633.37, 1746.2, 60000, 0.000023)
    cabos_caal(97) = Array("Olinda", 633.37, 1746.2, 60000, 0.000023)
    cabos_caal(98) = Array("Ourinhos", 633.37, 1746.2, 60000, 0.000023)
    cabos_caal(99) = Array("Parnaíba", 633.37, 1746.2, 60000, 0.000023)
    cabos_caal(100) = Array("Pelotas", 633.37, 1746.2, 60000, 0.000023)
    cabos_caal(101) = Array("Peruíbe", 658.71, 1816.1, 60000, 0.000023)
    cabos_caal(102) = Array("Registro", 658.71, 1816.1, 60000, 0.000023)
    cabos_caal(103) = Array("Santos", 658.71, 1816.1, 60000, 0.000023)
    cabos_caal(104) = Array("Sorocaba", 658.71, 1816.1, 60000, 0.000023)
    cabos_caal(105) = Array("Taubaté", 658.71, 1816.1, 60000, 0.000023)
    cabos_caal(106) = Array("Uberaba", 658.71, 1816.1, 60000, 0.000023)
    cabos_caal(107) = Array("Valinhos", 658.71, 1816.1, 60000, 0.000023)
    cabos_caal(108) = Array("Vassouras", 658.71, 1816.1, 60000, 0.000023)
    cabos_caal(109) = Array("Distrito Federal", 709.38, 1955.8, 60000, 0.000023)
    cabos_caal(110) = Array("Goiânia", 709.38, 1955.8, 60000, 0.000023)
    cabos_caal(111) = Array("Goiás", 709.38, 1955.8, 60000, 0.000023)
    cabos_caal(112) = Array("Brasília", 709.38, 1955.8, 60000, 0.000023)
    cabos_caal(113) = Array("Cuiabá", 760.05, 2095.5, 60000, 0.000023)
    cabos_caal(114) = Array("Florianópolis", 760.05, 2095.5, 60000, 0.000023)
    cabos_caal(115) = Array("Curitiba", 760.05, 2095.5, 60000, 0.000023)
    cabos_caal(116) = Array("Porto Alegre", 760.05, 2095.5, 60000, 0.000023)
    cabos_caal(117) = Array("Mato Grosso", 810.72, 2235.2, 60000, 0.000023)
    cabos_caal(118) = Array("Santa Catarina", 810.72, 2235.2, 60000, 0.000023)
    cabos_caal(119) = Array("Paraná", 810.72, 2235.2, 60000, 0.000023)
    cabos_caal(120) = Array("São Paulo", 810.72, 2235.2, 60000, 0.000023)
    cabos_caal(121) = Array("Niterói", 861.39, 2374.9, 60000, 0.000023)
    cabos_caal(122) = Array("Vitória", 861.39, 2374.9, 60000, 0.000023)
    cabos_caal(123) = Array("Belo Horizonte", 861.39, 2374.9, 60000, 0.000023)
    cabos_caal(124) = Array("Salvador", 861.39, 2374.9, 60000, 0.000023)
    cabos_caal(125) = Array("Rio de Janeiro", 886.72, 2444.7, 60000, 0.000023)
    cabos_caal(126) = Array("Espirito Santo", 886.72, 2444.7, 60000, 0.000023)
    cabos_caal(127) = Array("Minas Gerais", 886.72, 2444.7, 60000, 0.000023)
    cabos_caal(128) = Array("Bahia", 886.72, 2444.7, 60000, 0.000023)
    cabos_caal(129) = Array("Aracaju", 912.06, 2514.6, 60000, 0.000023)
    cabos_caal(130) = Array("Maceió", 912.06, 2514.6, 60000, 0.000023)
    cabos_caal(131) = Array("Recife", 912.06, 2514.6, 60000, 0.000023)
    cabos_caal(132) = Array("João Pessoa", 912.06, 191, 60000, 0.000023)
    cabos_caal(133) = Array("Sergipe", 962.73, 2654.3, 60000, 0.000023)
    cabos_caal(134) = Array("Alagoas", 962.73, 2654.3, 60000, 0.000023)
    cabos_caal(135) = Array("Pernambuco", 962.73, 2654.3, 60000, 0.000023)
    cabos_caal(136) = Array("Paraíba", 962.73, 2654.3, 60000, 0.000023)
    cabos_caal(137) = Array("Teresina", 1013.4, 2794, 60000, 0.000023)
    cabos_caal(138) = Array("Fortaleza", 1013.4, 2794, 60000, 0.000023)
    cabos_caal(139) = Array("São Luiz", 1013.4, 2794, 60000, 0.000023)
    cabos_caal(140) = Array("Natal", 1013.4, 2794, 60000, 0.000023)
    cabos_caal(141) = Array("Piauí", 1013.4, 2794, 60000, 0.000023)
    cabos_caal(142) = Array("Ceará", 1013.4, 2794, 60000, 0.000023)
    cabos_caal(143) = Array("Maranhão", 1013.4, 2794, 60000, 0.000023)
    cabos_caal(144) = Array("Rio Branco", 1140.07, 3174, 60000, 0.000023)
    cabos_caal(145) = Array("Porto Velho", 1140.07, 3174, 60000, 0.000023)
    cabos_caal(146) = Array("Manaus", 1140.07, 3174, 60000, 0.000023)
    cabos_caal(147) = Array("Amazonas", 1266.75, 3526.7, 60000, 0.000023)
    cabos_caal(148) = Array("Rondônia", 1266.75, 3526.7, 60000, 0.000023)
    cabos_caal(149) = Array("Acre", 1266.75, 3526.7, 60000, 0.000023)
    cabos_caal(150) = Array("Belém", 1393.4, 3879.4, 60000, 0.000023)
    cabos_caal(151) = Array("Macapá", 1393.4, 3879.4, 60000, 0.000023)
    cabos_caal(152) = Array("Bela Vista", 1393.4, 3879.4, 60000, 0.000023)
    cabos_caal(153) = Array("Pará", 1520.1, 4332.1, 60000, 0.000023)
    cabos_caal(154) = Array("Amapá", 1520.1, 4332.1, 60000, 0.000023)
    cabos_caal(155) = Array("Roraima", 1520.1, 4332.1, 60000, 0.000023)
    dados_caal = cabos_caal

End Function

Function dados_ca()
    Dim cabos_ca(48)
    cabos_ca(0) = Array("Sneezewort", 126.67, 349.2, 69055, 0.000023)
    cabos_ca(1) = Array("Daisy", 135.25, 373.5, 69055, 0.000023)
    cabos_ca(2) = Array("Valerian", 126.37, 348.4, 69055, 0.000023)
    cabos_ca(3) = Array("Laurel", 135.2, 372.8, 69055, 0.000023)
    cabos_ca(4) = Array("Peony", 151.85, 420.1, 69055, 0.000023)
    cabos_ca(5) = Array("Tulip", 170.48, 471.7, 69055, 0.000023)
    cabos_ca(6) = Array("Daffodil", 177.62, 491.5, 69055, 0.000023)
    cabos_ca(7) = Array("Canna", 202.09, 559.1, 69055, 0.000023)
    cabos_ca(8) = Array("Goldentuft", 228.14, 631.3, 69055, 0.000023)
    cabos_ca(9) = Array("Cosmos", 241.15, 667.4, 69055, 0.000023)
    cabos_ca(10) = Array("Zinnia", 253.3, 701, 69055, 0.000023)
    cabos_ca(11) = Array("Dahlia", 282.37, 781.2, 69055, 0.000023)
    cabos_ca(12) = Array("Syringa", 241.03, 664.6, 69055, 0.000023)
    cabos_ca(13) = Array("Hyacinth", 252.89, 697.2, 69055, 0.000023)
    cabos_ca(14) = Array("Mistletoe", 281.07, 774.9, 69055, 0.000023)
    cabos_ca(15) = Array("Meadowsweet", 303.18, 841.2, 69055, 0.000023)
    cabos_ca(16) = Array("Orchid", 322.24, 894.1, 69055, 0.000023)
    cabos_ca(17) = Array("Heuchera", 330.03, 909.9, 69055, 0.000023)
    cabos_ca(18) = Array("Verbena", 353.95, 982.2, 69055, 0.000023)
    cabos_ca(19) = Array("Violet", 362.11, 1005, 69055, 0.000023)
    cabos_ca(20) = Array("Petunia", 380.81, 1056, 69055, 0.000023)
    cabos_ca(21) = Array("Arbutus", 402.14, 1109, 69055, 0.000023)
    cabos_ca(22) = Array("Anemone", 444.27, 1233, 69055, 0.000023)
    cabos_ca(23) = Array("Cockscomb", 455.7, 1265, 69055, 0.000023)
    cabos_ca(24) = Array("Magnolia", 483.74, 1343, 69055, 0.000023)
    cabos_ca(25) = Array("Hawkweed", 507.74, 1400, 69055, 0.000023)
    cabos_ca(26) = Array("Bluebell", 522.42, 1449, 69055, 0.000023)
    cabos_ca(27) = Array("Flag", 354.45, 977.2, 69055, 0.000023)
    cabos_ca(28) = Array("Nasturtium", 362.31, 998.9, 69055, 0.000023)
    cabos_ca(29) = Array("Cattail", 380.99, 1050, 69055, 0.000023)
    cabos_ca(30) = Array("Lilac", 402.92, 1120, 69055, 0.000023)
    cabos_ca(31) = Array("Snapdragon", 457.44, 1261, 69055, 0.000023)
    cabos_ca(32) = Array("Goldenrod", 484.48, 1335, 69055, 0.000023)
    cabos_ca(33) = Array("Camelia", 506.04, 1395, 69055, 0.000023)
    cabos_ca(34) = Array("Larkspur", 524.9, 1447, 69055, 0.000023)
    cabos_ca(35) = Array("Marigold", 563.65, 1567, 69055, 0.000023)
    cabos_ca(36) = Array("Hawthorn", 603.78, 1677, 69055, 0.000023)
    cabos_ca(37) = Array("Narcissus", 645.29, 1793, 69055, 0.000023)
    cabos_ca(38) = Array("Columbine", 684.55, 1902, 69055, 0.000023)
    cabos_ca(39) = Array("Carnation", 724.97, 1998, 69055, 0.000023)
    cabos_ca(40) = Array("Gladiolus", 766.55, 2131, 69055, 0.000023)
    cabos_ca(41) = Array("Coreopsis", 805.36, 2239, 69055, 0.000023)
    cabos_ca(42) = Array("Jessamine", 885.84, 2442, 69055, 0.000023)
    cabos_ca(43) = Array("Cowslip", 1010.43, 2808, 69055, 0.000023)
    cabos_ca(44) = Array("Sagebrusch", 1137.83, 3168, 69055, 0.000023)
    cabos_ca(45) = Array("Lupine", 1266.76, 3521, 69055, 0.000023)
    cabos_ca(46) = Array("Bitterroot", 1396.29, 3886, 69055, 0.000023)
    cabos_ca(47) = Array("Trillium", 1517.13, 4264, 69055, 0.000023)
    cabos_ca(48) = Array("Bluebonnet", 1776.31, 4993, 69055, 0.000023)

    dados_ca = cabos_ca
End Function

Function dados_aco()
    Dim cabos_aco(6)
    
    cabos_aco(0) = Array("3/16", 17.795237426994, 108, 197000, 0.00001152)
    cabos_aco(1) = Array("1/4", 31.6692174435936, 180, 197000, 0.00001152)
    cabos_aco(2) = Array("5/16", 49.5143276539634, 305, 197000, 0.00001152)
    cabos_aco(3) = Array("3/8", 71.3305680581033, 406, 197000, 0.00001152)
    cabos_aco(4) = Array("7/16", 96.9433446442902, 593, 197000, 0.00001152)
    cabos_aco(5) = Array("1/2", 126.676869774374, 769, 197000, 0.00001152)
    cabos_aco(6) = Array("5/8", 198.057310615854, 1209, 197000, 0.00001152)

    dados_aco = cabos_aco
End Function

Sub principal()
    Set objeto = New cls_tensoes
    Set form = New form_tensoes
    Set objeto.formulario = form
    objeto.compr_ini = 0
    Set form.tensoes_cls = objeto
    form.Show 0
End Sub
