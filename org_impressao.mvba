Attribute VB_Name = "f_imprime"
Attribute VB_Base = "0{D468AE5A-DD44-44A4-ADC3-E183B5FE88FD}{CF04317C-2D0B-4E7E-B1F9-76ED112F58FB}"
Attribute VB_GlobalNameSpace = False
Attribute VB_Creatable = False
Attribute VB_PredeclaredId = True
Attribute VB_Exposed = False
Attribute VB_TemplateDerived = False
Attribute VB_Customizable = False

'------------------------------------------------------------------------------------------------------
'  OBJETO E CONSTANTES PARA A JANELA DE DIALOGO DE ABRIR
'------------------------------------------------------------------------------------------------------

Option Explicit
 
Private Const OFN_ALLOWMULTISELECT = &H200
Private Const OFN_CREATEPROMPT = &H2000
Private Const OFN_ENABLEHOOK = &H20
Private Const OFN_ENABLETEMPLATE = &H40
Private Const OFN_ENABLETEMPLATEHANDLE = &H80
Private Const OFN_EXPLORER = &H80000                         '  new look commdlg
Private Const OFN_EXTENSIONDIFFERENT = &H400
Private Const OFN_FILEMUSTEXIST = &H1000
Private Const OFN_HIDEREADONLY = &H4
Private Const OFN_LONGNAMES = &H200000                       '  force long names for 3.x modules
Private Const OFN_NOCHANGEDIR = &H8
Private Const OFN_NODEREFERENCELINKS = &H100000
Private Const OFN_NOLONGNAMES = &H40000                      '  force no long names for 4.x modules
Private Const OFN_NONETWORKBUTTON = &H20000
Private Const OFN_NOREADONLYRETURN = &H8000
Private Const OFN_NOTESTFILECREATE = &H10000
Private Const OFN_NOVALIDATE = &H100
Private Const OFN_OVERWRITEPROMPT = &H2
Private Const OFN_PATHMUSTEXIST = &H800
Private Const OFN_READONLY = &H1
Private Const OFN_SHAREAWARE = &H4000
Private Const OFN_SHAREFALLTHROUGH = 2
Private Const OFN_SHARENOWARN = 1
Private Const OFN_SHAREWARN = 0
Private Const OFN_SHOWHELP = &H10
 
Private Type OPENFILENAME
        lStructSize As Long
        hwndOwner As LongPtr
        hInstance As LongPtr
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        flags As Long
        nFileOffset As Integer
        nFileExtension As Integer
        lpstrDefExt As String
        lCustData As LongPtr
        lpfnHook As LongPtr
        lpTemplateName As String
        '#if (_WIN32_WINNT >= 0x0500)
        pvReserved As LongPtr
        dwReserved As Long
        FlagsEx As Long
'#endif // (_WIN32_WINNT >= 0x0500)
End Type


'#If VBA7 Then
Private Declare PtrSafe Function GetOpenFileName Lib "comdlg32.dll" Alias "GetOpenFileNameA" (pOpenfilename As OPENFILENAME) As Long
'#Else
'Private Declare Function GetOpenFileName Lib "comdlg32.dll" Alias "GetOpenFileNameA" (pOpenfilename As OPENFILENAME) As Long
'#End If

 
Private Function AddBS(ByVal sPath As String) As String
'------------------------------------------------------------------------------------------------------
'  FUNCAO PARA ADICIONAR A BARRA AOS CAMINHOS
'------------------------------------------------------------------------------------------------------
    If Right$(sPath, 1) <> "\" Then sPath = sPath & "\"
    AddBS = sPath
End Function


Private Sub b_adiciona_Click()
'------------------------------------------------------------------------------------------------------
'  ADICIONA ITENS NA LISTA DE ARQUIVOS
'------------------------------------------------------------------------------------------------------
    Dim tOPENFILENAME As OPENFILENAME
    Dim lResult As Long
    Dim vFiles As Variant
    Dim lIndex As Long, lStart As Long
    
    With tOPENFILENAME
        .lpstrTitle = "Escolha os arquivos"
        .flags = OFN_ALLOWMULTISELECT Or OFN_EXPLORER Or OFN_FILEMUSTEXIST Or OFN_LONGNAMES Or OFN_NOCHANGEDIR
        .hwndOwner = 0&
        .nMaxFile = 65535
        .lpstrInitialDir = ""
        .lpstrFilter = "Arquivos CAD (dgn, dwg, dxf)" & Chr(0) & "*.dgn;*.dwg;*.dxf" & Chr(0) & Chr(0)
        .lpstrFile = Space(65534) & Chr(0)
        .lStructSize = LenB(tOPENFILENAME)
    End With
    
    lResult = GetOpenFileName(tOPENFILENAME)
    
    If lResult > 0 Then
        With tOPENFILENAME
            vFiles = Split(Left(.lpstrFile, InStr(.lpstrFile, Chr(0) & Chr(0)) - 1), Chr(0))
        End With
        If UBound(vFiles) = 0 Then
            l_arquivos.AddItem
            l_arquivos.List(l_arquivos.ListCount - 1, 0) = vFiles(0)
            
        Else
            For lIndex = 1 To UBound(vFiles)
                l_arquivos.AddItem
                l_arquivos.List(l_arquivos.ListCount - 1, 0) = AddBS(vFiles(0)) & vFiles(lIndex)
            Next
        End If
        'extrai o caminho e atualiza a variavel
        destino.Value = Left(l_arquivos.List(l_arquivos.ListCount - 1, 0), InStrRev(l_arquivos.List(l_arquivos.ListCount - 1, 0), "\"))
    End If

End Sub

Private Sub B_imprime_Click()
    Dim num_des As Integer
    Dim i As Integer
    Dim j As Integer
    Dim nome_arq As String
    Dim arq As String
    Dim radical As String
    Dim resultado As String
    Dim ficha As New Collection

    num_des = 0

    For i = 0 To l_arquivos.ListCount - 1
        nome_arq = l_arquivos.List(i, 0) 'pega o caminho completo do arquivo
        
        'retira o caminho
        arq = Right(nome_arq, Len(nome_arq) - InStrRev(nome_arq, "\"))
        'extrai o radical
        radical = Left(arq, InStrRev(arq, "_") - 1)
        
        On Error Resume Next
        ficha.Add radical, radical
        
    Next i
    
    If ficha.Count > 0 Then
        'inicializa o Print Organizer
        CadInputQueue.SendCommand "mdl load bentley.printorganizer.dll"
        
        resultado = ""
        For i = 1 To ficha.Count
            'cria novo arquivo de saída
            CadInputQueue.SendCommand "PRINTORGANIZER NEW"
            CadInputQueue.SendCommand "PRINTORGANIZER PRINTERDRIVER pdf.pltcfg"
            
            For j = 0 To l_arquivos.ListCount - 1
                nome_arq = l_arquivos.List(j, 0) 'pega o caminho completo do arquivo
                
                'retira o caminho
                arq = Right(nome_arq, Len(nome_arq) - InStrRev(nome_arq, "\"))
                'extrai o radical
                radical = Left(arq, InStrRev(arq, "_") - 1)
                
                If radical = ficha(i) Then
                    'adiciona o arquivo se for da mesma ficha
                    CadInputQueue.SendCommand "PRINTORGANIZER ADD FILE " & Chr(34) & nome_arq & Chr(34)
                End If
                
            Next j
            
            If Right(destino.Value, 1) <> "\" Then
                destino = destino & "\"
            End If
            
            CadInputQueue.SendCommand "PRINTORGANIZER APPLYPRINTSTYLE ALL " & print_style.Value
            CadInputQueue.SendCommand "PRINTORGANIZER SUBMITAS SINGLE"
            'define o nome do arquivo de saída
            CadInputQueue.SendCommand "PRINTORGANIZER PRINTDESTINATION " & Chr(34) & destino & ficha(i) & ".pdf" & Chr(34)
            CadInputQueue.SendCommand "PRINTORGANIZER PRINT ALL"
            
            resultado = resultado & ficha(i) & vbCrLf
        Next i
        
        'encerra o Print Organizer
        CadInputQueue.SendCommand "PRINTORGANIZER EXIT"
        
        MsgBox "Pronto! fichas criadas:" & vbCrLf & resultado
        
    Else
        MsgBox "Sem arquivos para impressão", vbCritical
    End If
        
End Sub

Private Sub b_limpa_Click()
    l_arquivos.Clear
End Sub



Private Sub UserForm_Initialize()
    If ActiveWorkspace.IsConfigurationVariableDefined("P_STYLE") Then
        print_style.Value = ActiveWorkspace.ConfigurationVariableValue("P_STYLE")
    Else
        print_style.Value = ""
    End If
End Sub

Private Sub UserForm_Terminate()
    ActiveWorkspace.AddConfigurationVariable "P_STYLE", print_style.Value, True
End Sub

Attribute VB_Name = "org_impr"
Function regex(strInput As String, matchPattern As String, Optional ByVal outputPattern As String = "$0") As Variant
    Dim inputRegexObj As New VBScript_RegExp_55.RegExp, outputRegexObj As New VBScript_RegExp_55.RegExp, outReplaceRegexObj As New VBScript_RegExp_55.RegExp
    Dim inputMatches As Object, replaceMatches As Object, replaceMatch As Object
    Dim replaceNumber As Integer

    With inputRegexObj
        .Global = True
        .MultiLine = True
        .IgnoreCase = False
        .Pattern = matchPattern
    End With
    With outputRegexObj
        .Global = True
        .MultiLine = True
        .IgnoreCase = False
        .Pattern = "\$(\d+)"
    End With
    With outReplaceRegexObj
        .Global = True
        .MultiLine = True
        .IgnoreCase = False
    End With

    Set inputMatches = inputRegexObj.Execute(strInput)
    If inputMatches.Count = 0 Then
        regex = False
    Else
        Set replaceMatches = outputRegexObj.Execute(outputPattern)
        For Each replaceMatch In replaceMatches
            replaceNumber = replaceMatch.SubMatches(0)
            outReplaceRegexObj.Pattern = "\$" & replaceNumber

            If replaceNumber = 0 Then
                outputPattern = outReplaceRegexObj.Replace(outputPattern, inputMatches(0).Value)
            Else
                If replaceNumber > inputMatches(0).SubMatches.Count Then
                    regex = CVErr(xlErrValue)
                    Exit Function
                Else
                    outputPattern = outReplaceRegexObj.Replace(outputPattern, inputMatches(0).SubMatches(replaceNumber - 1))
                End If
            End If
        Next
        regex = outputPattern
    End If
End Function

Sub executa()
    Load f_imprime
    f_imprime.Show 0
End Sub
