Attribute VB_Name = "cl_interlig"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Public lista_interlig As Collection
Public rev As String
Public ck_inv As CheckBox
Public ck_y As CheckBox
Public engates As int_p
Public lista_cabos As ListBox

Private borne_pos As Point3d
Private borne_ofs As Point3d
Private id_ofs As Double
Private dest_ofs As Double
Private cabo_ofs As Point3d
Private passo As Double

Private ponto_ent As Point3d


Private num_pts As Integer

Private Sub IPrimitiveCommandEvents_Cleanup()

End Sub

Private Sub IPrimitiveCommandEvents_DataPoint(Point As Point3d, ByVal View As View)
    
    Dim condutor As Collection
    Dim condutores As Collection
    Dim ponto_atual As Point3d
    Dim borne As CellElement
    Dim cabo_id As CellElement
    Dim engate As CellElement
    Dim cond_id As CellElement
    Dim cond_dest As CellElement
    Dim tag As TagElement
    Dim arco As ArcElement
    Dim centro As Point3d
    Dim arco_fim As Point3d
    Dim l_borne As LineElement
    Dim l_id As LineElement
    Dim l_cabo As LineElement
    Dim l_cabo_pt1 As Point3d
    Dim l_cabo_pt2 As Point3d
    Dim nivel As String
    Dim engate_id As String
    Dim ng As NamedGroupElement
    
    Dim pt2 As Point3d
    Dim pt3 As Point3d
    Dim i As Integer
    Dim x_min, y_min, x_max, y_max As Double
    
    Dim cabo As Collection
    Dim nome_cabo As String
    
    'If lista_cabos.ListIndex >= 0 Then
    nome_cabo = lista_cabos.List(lista_cabos.ListIndex)
    Set cabo = lista_interlig(nome_cabo)
    
    Set condutores = cabo("cond")
    x_min = 0
    y_min = 0
    x_max = 0
    y_max = 0
    
    For Each condutor In condutores
        If CInt(condutor("usado")) > 0 Then
            If i = 0 Then
                x_min = condutor("x")
                y_min = condutor("y")
                x_max = condutor("x")
                y_max = condutor("y")
            Else
                If condutor("x") < x_min Then x_min = condutor("x")
                If condutor("x") > x_max Then x_max = condutor("x")
                If condutor("y") < y_min Then y_min = condutor("y")
                If condutor("y") > y_max Then y_max = condutor("y")
            End If
            i = i + 1
        End If
    Next condutor
    
    nivel = ActiveSettings.Level.Name
    
    If num_pts = 0 Then
        borne_pos.X = Point.X
        borne_pos.Y = Point.Y
        borne_pos.Z = Point.Z
    ElseIf num_pts = 1 Then
        ponto_ent = borne_pos
    ElseIf num_pts = 2 Then
        If ck_inv.Value = False Then
            ponto_atual.X = borne_pos.X + borne_ofs.X + dest_ofs + 20#
        Else
            ponto_atual.X = borne_pos.X - borne_ofs.X - dest_ofs - 20#
        End If
        ponto_atual.Y = borne_pos.Y + borne_ofs.Y
        ponto_atual.Z = borne_pos.Z + borne_ofs.Z
        ponto_ent = ponto_atual
        CommandState.AccuDrawHints.SetOrigin ponto_atual
        
    ElseIf num_pts = 3 Then
        If ck_inv.Value = False Then
            ponto_atual.X = borne_pos.X + borne_ofs.X + dest_ofs + 20# + id_ofs + 2# + 4# + cabo_ofs.X
        Else
            ponto_atual.X = borne_pos.X - borne_ofs.X - dest_ofs - 20# - id_ofs - 2# - 4# + cabo_ofs.X
        End If
        If ck_y.Value = False Then
            ponto_atual.Y = borne_pos.Y + borne_ofs.Y + 2# + 2# + cabo_ofs.Y
        Else
            ponto_atual.Y = borne_pos.Y + borne_ofs.Y - 2# - 2# + cabo_ofs.Y - (y_max - y_min)
        End If
        ponto_atual.Z = borne_pos.Z + borne_ofs.Z + cabo_ofs.Z
        ponto_ent = ponto_atual
        CommandState.AccuDrawHints.SetOrigin ponto_atual
        
    End If
    
    If IsCellLibraryAttached And num_pts = 4 Then
        
        If ck_y.Value = False Then
            ponto_atual.Y = borne_pos.Y + borne_ofs.Y + 2# + 2# + cabo_ofs.Y
        Else
            ponto_atual.Y = borne_pos.Y + borne_ofs.Y - 2# - 2# + cabo_ofs.Y - (y_max - y_min)
        End If
        
        ponto_atual.Z = borne_pos.Z + borne_ofs.Z + cabo_ofs.Z
        
        If ck_inv.Value = False Then
            ponto_atual.X = borne_pos.X + borne_ofs.X + dest_ofs + 20# + id_ofs + 2# + 4# + cabo_ofs.X
            Set cabo_id = CreateCellElement3("cabo", ponto_atual, False)
        Else
            ponto_atual.X = borne_pos.X - borne_ofs.X - dest_ofs - 20# - id_ofs - 2# - 4# + cabo_ofs.X
            
            Set cabo_id = CreateCellElement3("i_cabo", ponto_atual, False)
        End If
        
        ActiveModelReference.AddElement cabo_id
        cell_level cabo_id, nivel
        
        
        Set tag = get_tag_name(cabo_id, "cabo")
        If Not (tag Is Nothing) Then
            tag.Value = cabo("id")
            tag.Redraw
            tag.Rewrite
            
        End If
        Set tag = get_tag_name(cabo_id, "num_cond")
        If Not (tag Is Nothing) Then
            tag.Value = cabo("num")
            tag.Redraw
            tag.Rewrite
        End If
        Set tag = get_tag_name(cabo_id, "descr")
        If Not (tag Is Nothing) Then
            tag.Value = cabo("descr")
            tag.Redraw
            tag.Rewrite
        End If
        Set tag = get_tag_name(cabo_id, "des")
        If Not (tag Is Nothing) Then
            tag.Value = cabo("des")
            tag.Redraw
            tag.Rewrite
        End If
        Set tag = get_tag_name(cabo_id, "rev")
        If Not (tag Is Nothing) Then
            tag.Value = rev
            tag.Redraw
            tag.Rewrite
        End If
        
        If ck_inv.Value = False Then
            ponto_atual.X = borne_pos.X + borne_ofs.X + dest_ofs + 20# + id_ofs + 2# + 4#
        Else
            ponto_atual.X = borne_pos.X - borne_ofs.X - dest_ofs - 20# - id_ofs - 2# - 4#
        End If
        
        centro.X = ponto_atual.X
        If ck_y.Value = False Then
            centro.Y = ponto_atual.Y - 2
        Else
            centro.Y = ponto_atual.Y + 2
        End If
        centro.Z = ponto_atual.Z
        
        If ck_inv.Value = False Then
            arco_fim.X = ponto_atual.X - 2
        Else
            arco_fim.X = ponto_atual.X + 2
        End If
        arco_fim.Y = centro.Y
        arco_fim.Z = centro.Z
        
        l_cabo_pt1.X = arco_fim.X
        l_cabo_pt1.Y = arco_fim.Y
        l_cabo_pt1.Z = arco_fim.Z
        
        l_cabo_pt2.X = arco_fim.X
        l_cabo_pt2.Y = arco_fim.Y
        l_cabo_pt2.Z = arco_fim.Z
        
        If ck_inv.Value Xor ck_y.Value Then
            Set arco = CreateArcElement1(Nothing, arco_fim, centro, ponto_atual)
        Else
            Set arco = CreateArcElement1(Nothing, ponto_atual, centro, arco_fim)
        End If
        ActiveModelReference.AddElement arco
        
        pt2 = ponto_atual
        pt2.X = pt2.X + cabo_ofs.X
        Set l_cabo = CreateLineElement2(Nothing, pt2, ponto_atual)
        ActiveModelReference.AddElement l_cabo
        
        If CInt(cabo("usados")) < condutores.Count Then
            engate_id = cabo("engate")
            If engate_id = "" Then
                engate_id = "E" & CStr(engates.Value)
                cabo.Remove "engate"
                cabo.Add engate_id, "engate"
                engates.Value = engates.Value + 1
            End If
            If ck_inv.Value = False Then
                ponto_atual.X = borne_pos.X + borne_ofs.X + dest_ofs + 20# + id_ofs + 2# + 4# + cabo_ofs.X
                
                Set engate = CreateCellElement3("cabo_engate", ponto_atual, False)
            Else
                ponto_atual.X = borne_pos.X - borne_ofs.X - dest_ofs - 20# - id_ofs - 2# - 4# + cabo_ofs.X
                
                Set engate = CreateCellElement3("i_cabo_engate", ponto_atual, False)
            End If
            ActiveModelReference.AddElement engate
            
            cell_level engate, nivel
            
            
            Set tag = get_tag_name(engate, "engate")
            If Not (tag Is Nothing) Then
                tag.Value = engate_id
                tag.Redraw
                tag.Rewrite
            End If
            Set tag = get_tag_name(engate, "cabo")
            If Not (tag Is Nothing) Then
                tag.Value = cabo("id")
                tag.Redraw
                tag.Rewrite
            End If
            Set tag = get_tag_name(engate, "rev")
            If Not (tag Is Nothing) Then
                tag.Value = rev
                tag.Redraw
                tag.Rewrite
            End If
        End If
        
        
        
        For Each condutor In condutores
            If CInt(condutor("usado")) > 0 Then
                'Set borne = CreateCellElement3("borne", borne_pos, False)
                'borne.Redraw DrawMode
                If ck_inv.Value = False Then
                    pt2.X = borne_pos.X + (condutor("x") - x_max)
                Else
                    pt2.X = borne_pos.X + (condutor("x") - x_min)
                End If
                pt2.Y = borne_pos.Y + (condutor("y") - y_max)
                pt2.Z = borne_pos.Z
                
                If ck_inv.Value = False Then
                    ponto_atual.X = borne_pos.X + borne_ofs.X + (condutor("x") - x_max)
                Else
                    ponto_atual.X = borne_pos.X - borne_ofs.X + (condutor("x") - x_min)
                End If
                ponto_atual.Y = borne_pos.Y + borne_ofs.Y + (condutor("y") - y_max)
                ponto_atual.Z = borne_pos.Z + borne_ofs.Z
                
                Set l_cabo = CreateLineElement2(Nothing, pt2, ponto_atual)
                ActiveModelReference.AddElement l_cabo
                
                pt2 = ponto_atual
                
                If ck_inv.Value = False Then
                    ponto_atual.X = borne_pos.X + borne_ofs.X + dest_ofs
                Else
                    ponto_atual.X = borne_pos.X - borne_ofs.X - dest_ofs
                End If
                ponto_atual.Y = borne_pos.Y + borne_ofs.Y + (condutor("y") - y_max)
                ponto_atual.Z = borne_pos.Z + borne_ofs.Z
                
                Set l_cabo = CreateLineElement2(Nothing, pt2, ponto_atual)
                ActiveModelReference.AddElement l_cabo
                
                pt2 = ponto_atual
                If ck_inv.Value = False Then
                    Set cond_dest = CreateCellElement3("cond_dest", ponto_atual, False)
                Else
                    Set cond_dest = CreateCellElement3("i_cond_dest", ponto_atual, False)
                End If
                ActiveModelReference.AddElement cond_dest
                
                cell_level cond_dest, nivel
                Set tag = get_tag_name(cond_dest, "dest")
                If Not (tag Is Nothing) Then
                    tag.Value = condutor("dest")
                    tag.Redraw
                    tag.Rewrite
                End If
                Set tag = get_tag_name(cond_dest, "orig")
                If Not (tag Is Nothing) Then
                    tag.Value = condutor("orig")
                    tag.Redraw
                    tag.Rewrite
                End If
                Set tag = get_tag_name(cond_dest, "cabo")
                If Not (tag Is Nothing) Then
                    tag.Value = cabo("id")
                    tag.Redraw
                    tag.Rewrite
                End If
                Set tag = get_tag_name(cond_dest, "condutor")
                If Not (tag Is Nothing) Then
                    tag.Value = condutor("id")
                    tag.Redraw
                    tag.Rewrite
                End If
                Set tag = get_tag_name(cond_dest, "rev")
                If Not (tag Is Nothing) Then
                    tag.Value = rev
                    tag.Redraw
                    tag.Rewrite
                End If
                
                If ck_inv.Value = False Then
                    ponto_atual.X = borne_pos.X + borne_ofs.X + dest_ofs + 20# + id_ofs
                    pt2.X = pt2.X + 20#
                Else
                    ponto_atual.X = borne_pos.X - borne_ofs.X - dest_ofs - 20# - id_ofs
                    pt2.X = pt2.X - 20#
                End If
                ponto_atual.Y = borne_pos.Y + borne_ofs.Y + (condutor("y") - y_max)
                ponto_atual.Z = borne_pos.Z + borne_ofs.Z
                
                
                Set l_cabo = CreateLineElement2(Nothing, pt2, ponto_atual)
                ActiveModelReference.AddElement l_cabo
                
                
                If ck_inv.Value = False Then
                    Set cond_id = CreateCellElement3("cond_id", ponto_atual, False)
                Else
                    Set cond_id = CreateCellElement3("i_cond_id", ponto_atual, False)
                End If
                ActiveModelReference.AddElement cond_id
                
                cell_level cond_id, nivel
                Set tag = get_tag_name(cond_id, "condutor")
                If Not (tag Is Nothing) Then
                    tag.Value = condutor("id")
                    tag.Redraw
                    tag.Rewrite
                End If
                Set tag = get_tag_name(cond_id, "dest")
                If Not (tag Is Nothing) Then
                    tag.Value = condutor("dest")
                    tag.Redraw
                    tag.Rewrite
                End If
                Set tag = get_tag_name(cond_id, "orig")
                If Not (tag Is Nothing) Then
                    tag.Value = condutor("orig")
                    tag.Redraw
                    tag.Rewrite
                End If
                Set tag = get_tag_name(cond_id, "cabo")
                If Not (tag Is Nothing) Then
                    tag.Value = cabo("id")
                    tag.Redraw
                    tag.Rewrite
                End If
                Set tag = get_tag_name(cond_id, "rev")
                If Not (tag Is Nothing) Then
                    tag.Value = rev
                    tag.Redraw
                    tag.Rewrite
                End If
                
                If ck_inv.Value = False Then
                    ponto_atual.X = ponto_atual.X + 2
                    arco_fim.X = ponto_atual.X + 2
                Else
                    ponto_atual.X = ponto_atual.X - 2
                    arco_fim.X = ponto_atual.X - 2
                End If
                
                centro.X = ponto_atual.X
                If ck_y.Value = False Then
                    centro.Y = ponto_atual.Y + 2
                Else
                    centro.Y = ponto_atual.Y - 2
                End If
                centro.Z = ponto_atual.Z
                
                arco_fim.Y = centro.Y
                arco_fim.Z = ponto_atual.Z
                
                If ck_inv.Value Xor ck_y.Value Then
                    Set arco = CreateArcElement1(Nothing, arco_fim, centro, ponto_atual)
                Else
                    Set arco = CreateArcElement1(Nothing, ponto_atual, centro, arco_fim)
                End If
                    
                ActiveModelReference.AddElement arco
                
                
                
            End If
        Next condutor
        If ck_y.Value = False Then
            l_cabo_pt2.Y = l_cabo_pt2.Y + y_min - y_max - cabo_ofs.Y
        Else
            l_cabo_pt2.Y = l_cabo_pt2.Y - y_min + y_max - cabo_ofs.Y
        End If
        Set l_cabo = CreateLineElement2(Nothing, l_cabo_pt1, l_cabo_pt2)
        ActiveModelReference.AddElement l_cabo
        
        lista_cabos.List(lista_cabos.ListIndex, 3) = "x"
        If lista_cabos.ListIndex < lista_cabos.ListCount Then
            If CInt(lista_cabos.List(lista_cabos.ListIndex + 1, 1)) > 0 Then
                lista_cabos.ListIndex = lista_cabos.ListIndex + 1
            Else
                CommandState.StartDefaultCommand
            End If
        Else
            CommandState.StartDefaultCommand
        End If
        
        borne_ofs.X = 0#
        borne_ofs.Y = 0#
        borne_ofs.Z = 0#
        id_ofs = 0#
        dest_ofs = 0#
        cabo_ofs.X = 0#
        cabo_ofs.Y = 0#
        cabo_ofs.Z = 0#
        passo = 6#
        num_pts = 0
        
    Else
        num_pts = num_pts + 1
    End If
    
    
    
End Sub


Private Sub IPrimitiveCommandEvents_Dynamics(Point As Point3d, ByVal View As View, ByVal DrawMode As MsdDrawingMode)
    Dim condutor As Collection
    Dim condutores As Collection
    Dim ponto_atual As Point3d
    Dim borne As CellElement
    Dim cabo_id As CellElement
    Dim engate As CellElement
    Dim cond_id As CellElement
    Dim cond_dest As CellElement
    Dim tag As TagElement
    Dim arco As ArcElement
    Dim centro As Point3d
    Dim arco_fim As Point3d
    Dim l_borne As LineElement
    Dim l_id As LineElement
    Dim l_cabo As LineElement
    Dim l_cabo_pt1 As Point3d
    Dim l_cabo_pt2 As Point3d
    
    Dim pt2 As Point3d
    Dim i As Integer
    Dim x_min, y_min, x_max, y_max As Double
    Dim total_usados As Integer
    
    Dim cabo As Collection
    Dim nome_cabo As String
    
    'If lista_cabos.ListIndex >= 0 Then
    nome_cabo = lista_cabos.List(lista_cabos.ListIndex)
    Set cabo = lista_interlig(nome_cabo)
    
    If IsCellLibraryAttached Then
        'CommandState.ParseAll = True
        Set condutores = cabo("cond")
        
        x_min = 0
        y_min = 0
        x_max = 0
        y_max = 0
        
        For Each condutor In condutores
            If CInt(condutor("usado")) > 0 Then
                If i = 0 Then
                    x_min = condutor("x")
                    y_min = condutor("y")
                    x_max = condutor("x")
                    y_max = condutor("y")
                Else
                    If condutor("x") < x_min Then x_min = condutor("x")
                    If condutor("x") > x_max Then x_max = condutor("x")
                    If condutor("y") < y_min Then y_min = condutor("y")
                    If condutor("y") > y_max Then y_max = condutor("y")
                End If
                i = i + 1
            End If
        Next condutor
        
        If num_pts = 0 Then
            borne_pos.X = Point.X
            borne_pos.Y = Point.Y
            borne_pos.Z = Point.Z
        ElseIf num_pts = 1 Then
            If ck_inv.Value = False Then
                borne_ofs.X = Point.X - borne_pos.X
                borne_ofs.Y = Point.Y - borne_pos.Y
                borne_ofs.Z = Point.Z - borne_pos.Z
            Else
                borne_ofs.X = borne_pos.X - Point.X
                borne_ofs.Y = Point.Y - borne_pos.Y
                borne_ofs.Z = Point.Z - borne_pos.Z
            End If
        ElseIf num_pts = 2 Then
            If ck_inv.Value = False Then
                dest_ofs = Point.X - (borne_pos.X + borne_ofs.X)
            Else
                dest_ofs = (borne_pos.X - borne_ofs.X) - Point.X
            End If
        ElseIf num_pts = 3 Then
            If ck_inv.Value = False Then
                id_ofs = Point.X - ponto_ent.X
            Else
                id_ofs = ponto_ent.X - Point.X
            End If
        ElseIf num_pts = 4 Then
            cabo_ofs.X = Point.X - ponto_ent.X
            cabo_ofs.Y = Point.Y - ponto_ent.Y
            cabo_ofs.Z = Point.Z - ponto_ent.Z
        End If
        
        If ck_y.Value = False Then
            ponto_atual.Y = borne_pos.Y + borne_ofs.Y + 2# + 2# + cabo_ofs.Y
        Else
            ponto_atual.Y = borne_pos.Y + borne_ofs.Y - 2# - 2# + cabo_ofs.Y - (y_max - y_min)
        End If
        
        ponto_atual.Z = borne_pos.Z + borne_ofs.Z + cabo_ofs.Z
        
        If ck_inv.Value = False Then
            ponto_atual.X = borne_pos.X + borne_ofs.X + dest_ofs + 20# + id_ofs + 2# + 4# + cabo_ofs.X
            
            
            Set cabo_id = CreateCellElement3("cabo", ponto_atual, False)
            cabo_id.Redraw DrawMode
            
            ponto_atual.X = borne_pos.X + borne_ofs.X + dest_ofs + 20# + id_ofs + 2# + 4#
            
            centro.X = ponto_atual.X
            If ck_y.Value = False Then
                centro.Y = ponto_atual.Y - 2
            Else
                centro.Y = ponto_atual.Y + 2
            End If
            centro.Z = ponto_atual.Z
            
            arco_fim.X = ponto_atual.X - 2
            arco_fim.Y = centro.Y
            arco_fim.Z = centro.Z
            
        Else
            ponto_atual.X = borne_pos.X - borne_ofs.X - dest_ofs - 20# - id_ofs - 2# - 4# + cabo_ofs.X
            
            Set cabo_id = CreateCellElement3("i_cabo", ponto_atual, False)
            'pt2 = ponto_atual
            'pt2.Y = pt2.Y + 1
            'cabo_id.Mirror ponto_atual, pt2
            cabo_id.Redraw DrawMode
            
            ponto_atual.X = borne_pos.X - borne_ofs.X - dest_ofs - 20# - id_ofs - 2# - 4#
            
            centro.X = ponto_atual.X
            If ck_y.Value = False Then
                centro.Y = ponto_atual.Y - 2
            Else
                centro.Y = ponto_atual.Y + 2
            End If
            centro.Z = ponto_atual.Z
            
            arco_fim.X = ponto_atual.X + 2
            arco_fim.Y = centro.Y
            arco_fim.Z = centro.Z
            
            
        End If
        l_cabo_pt1.X = arco_fim.X
        l_cabo_pt1.Y = arco_fim.Y
        l_cabo_pt1.Z = arco_fim.Z
        
        l_cabo_pt2.X = arco_fim.X
        l_cabo_pt2.Y = arco_fim.Y
        l_cabo_pt2.Z = arco_fim.Z
        
        If ck_inv.Value Xor ck_y.Value Then
            Set arco = CreateArcElement1(cabo_id, arco_fim, centro, ponto_atual)
        Else
            Set arco = CreateArcElement1(cabo_id, ponto_atual, centro, arco_fim)
        End If
        arco.Redraw DrawMode
        
        pt2 = ponto_atual
        pt2.X = pt2.X + cabo_ofs.X
        Set l_cabo = CreateLineElement2(cabo_id, pt2, ponto_atual)
        l_cabo.Redraw DrawMode
    
    
        
        
        total_usados = condutores.Count
        If CInt(cabo("usados")) < total_usados Then
        
            If ck_y.Value = False Then
                ponto_atual.Y = borne_pos.Y + borne_ofs.Y + 2# + 2# + cabo_ofs.Y
            Else
                ponto_atual.Y = borne_pos.Y + borne_ofs.Y - 2# - 2# + cabo_ofs.Y - (y_max - y_min)
            End If
            ponto_atual.Z = borne_pos.Z + borne_ofs.Z + cabo_ofs.Z
            If ck_inv.Value = False Then
                ponto_atual.X = borne_pos.X + borne_ofs.X + dest_ofs + 20# + id_ofs + 2# + 4# + cabo_ofs.X
                Set engate = CreateCellElement3("cabo_engate", ponto_atual, False)
                engate.Redraw DrawMode
            Else
                ponto_atual.X = borne_pos.X - borne_ofs.X - dest_ofs - 20# - id_ofs - 2# - 4# + cabo_ofs.X
                Set engate = CreateCellElement3("i_cabo_engate", ponto_atual, False)
                engate.Redraw DrawMode
            End If
        End If
        
        
        
        
        For Each condutor In condutores
            If CInt(condutor("usado")) > 0 Then
                'Set borne = CreateCellElement3("borne", borne_pos, False)
                'borne.Redraw DrawMode
                If ck_inv.Value = False Then
                    If num_pts = 0 Then
                        pt2.X = condutor("x") + 16#
                        pt2.Y = condutor("y") - 3#
                        pt2.Z = 0
                    Else
                        pt2.X = borne_pos.X + (condutor("x") - x_max)
                        pt2.Y = borne_pos.Y + (condutor("y") - y_max)
                        pt2.Z = borne_pos.Z
                    End If
                    
                    
                    ponto_atual.X = borne_pos.X + borne_ofs.X + (condutor("x") - x_max)
                    ponto_atual.Y = borne_pos.Y + borne_ofs.Y + (condutor("y") - y_max)
                    ponto_atual.Z = borne_pos.Z + borne_ofs.Z
                    
                    Set l_cabo = CreateLineElement2(cabo_id, pt2, ponto_atual)
                    l_cabo.Redraw DrawMode
                    pt2 = ponto_atual
                    
                    ponto_atual.X = borne_pos.X + borne_ofs.X + dest_ofs
                    ponto_atual.Y = borne_pos.Y + borne_ofs.Y + (condutor("y") - y_max)
                    ponto_atual.Z = borne_pos.Z + borne_ofs.Z
                    
                    Set l_cabo = CreateLineElement2(cabo_id, pt2, ponto_atual)
                    l_cabo.Redraw DrawMode
                    pt2 = ponto_atual
                    
                    Set cond_dest = CreateCellElement3("cond_dest", ponto_atual, False)
                    cond_dest.Redraw DrawMode
                    
                    ponto_atual.X = borne_pos.X + borne_ofs.X + dest_ofs + 20# + id_ofs
                    ponto_atual.Y = borne_pos.Y + borne_ofs.Y + (condutor("y") - y_max)
                    ponto_atual.Z = borne_pos.Z + borne_ofs.Z
                    
                    pt2.X = pt2.X + 20#
                    Set l_cabo = CreateLineElement2(cabo_id, pt2, ponto_atual)
                    l_cabo.Redraw DrawMode
                    
                    
                    Set cond_id = CreateCellElement3("cond_id", ponto_atual, False)
                    cond_id.Redraw DrawMode
                    
                    ponto_atual.X = ponto_atual.X + 2
                    arco_fim.X = ponto_atual.X + 2
                    
                Else
                    If num_pts = 0 Then
                        pt2.X = condutor("x")
                        pt2.Y = condutor("y") - 3#
                        pt2.Z = 0
                    Else
                        pt2.X = borne_pos.X + (condutor("x") - x_min)
                        pt2.Y = borne_pos.Y + (condutor("y") - y_max)
                        pt2.Z = borne_pos.Z
                    End If
                    
                    
                    ponto_atual.X = borne_pos.X - borne_ofs.X + (condutor("x") - x_min)
                    ponto_atual.Y = borne_pos.Y + borne_ofs.Y + (condutor("y") - y_max)
                    ponto_atual.Z = borne_pos.Z + borne_ofs.Z
                    
                    Set l_cabo = CreateLineElement2(cabo_id, pt2, ponto_atual)
                    l_cabo.Redraw DrawMode
                    pt2 = ponto_atual
                    
                    ponto_atual.X = borne_pos.X - borne_ofs.X - dest_ofs
                    ponto_atual.Y = borne_pos.Y + borne_ofs.Y + (condutor("y") - y_max)
                    ponto_atual.Z = borne_pos.Z + borne_ofs.Z
                    
                    Set l_cabo = CreateLineElement2(cabo_id, pt2, ponto_atual)
                    l_cabo.Redraw DrawMode
                    pt2 = ponto_atual
                    
                    Set cond_dest = CreateCellElement3("i_cond_dest", ponto_atual, False)
                    cond_dest.Redraw DrawMode
                    
                    ponto_atual.X = borne_pos.X - borne_ofs.X - dest_ofs - 20# - id_ofs
                    ponto_atual.Y = borne_pos.Y + borne_ofs.Y + (condutor("y") - y_max)
                    ponto_atual.Z = borne_pos.Z + borne_ofs.Z
                    
                    pt2.X = pt2.X - 20#
                    Set l_cabo = CreateLineElement2(cabo_id, pt2, ponto_atual)
                    l_cabo.Redraw DrawMode
                    
                    
                    Set cond_id = CreateCellElement3("i_cond_id", ponto_atual, False)
                    cond_id.Redraw DrawMode
                    
                    ponto_atual.X = ponto_atual.X - 2
                    arco_fim.X = ponto_atual.X - 2
                    
                End If
                centro.X = ponto_atual.X
                If ck_y.Value = False Then
                    centro.Y = ponto_atual.Y + 2
                Else
                    centro.Y = ponto_atual.Y - 2
                End If
                centro.Z = ponto_atual.Z
                
                arco_fim.Y = centro.Y
                arco_fim.Z = ponto_atual.Z
                
                If ck_inv.Value Xor ck_y.Value Then
                    Set arco = CreateArcElement1(cabo_id, arco_fim, centro, ponto_atual)
                Else
                    Set arco = CreateArcElement1(cabo_id, ponto_atual, centro, arco_fim)
                End If
                arco.Redraw DrawMode
            End If
        Next condutor
        
        If ck_y.Value = False Then
            l_cabo_pt2.Y = l_cabo_pt2.Y + y_min - y_max - cabo_ofs.Y
        Else
            l_cabo_pt2.Y = l_cabo_pt2.Y - y_min + y_max - cabo_ofs.Y
        End If
        Set l_cabo = CreateLineElement2(cabo_id, l_cabo_pt1, l_cabo_pt2)
        l_cabo.Redraw DrawMode
    End If
    
End Sub

Private Sub IPrimitiveCommandEvents_Keyin(ByVal Keyin As String)

End Sub

Private Sub IPrimitiveCommandEvents_Reset()
    'CommandState.ParseAll = False
    CommandState.StartDefaultCommand
End Sub

Private Sub IPrimitiveCommandEvents_Start()
    ShowCommand "Interligação - Insere cabo"
    ShowPrompt "Selecione o ponto desejado"
    
    borne_ofs.X = 0#
    borne_ofs.Y = 0#
    borne_ofs.Z = 0#
    id_ofs = 0#
    dest_ofs = 0#
    cabo_ofs.X = 0#
    cabo_ofs.Y = 0#
    cabo_ofs.Z = 0#
    passo = 6#
    num_pts = 0
    'engates = 1
    
    AttachCellLibrary "D:\microstat\fiacao.cel"
    
    
    CommandState.StartDynamics
    
    CommandState.EnableAccuSnap
    'CommandState.ParseAll = True
End Sub

Attribute VB_Name = "f_fiacao"
Attribute VB_Base = "0{CABC7708-AEB2-4A84-AE37-4E74B14D9D4C}{62238FDA-BBF0-4A7C-9B1A-9604DF1F8BC3}"
Attribute VB_GlobalNameSpace = False
Attribute VB_Creatable = False
Attribute VB_PredeclaredId = True
Attribute VB_Exposed = False
Attribute VB_TemplateDerived = False
Attribute VB_Customizable = False

'------------------------------------------------------------------------------------------------------
'  OBJETO E CONSTANTES PARA A JANELA DE DIALOGO DE ABRIR
'------------------------------------------------------------------------------------------------------

Option Explicit
 
Private Const OFN_ALLOWMULTISELECT = &H200
Private Const OFN_CREATEPROMPT = &H2000
Private Const OFN_ENABLEHOOK = &H20
Private Const OFN_ENABLETEMPLATE = &H40
Private Const OFN_ENABLETEMPLATEHANDLE = &H80
Private Const OFN_EXPLORER = &H80000                         '  new look commdlg
Private Const OFN_EXTENSIONDIFFERENT = &H400
Private Const OFN_FILEMUSTEXIST = &H1000
Private Const OFN_HIDEREADONLY = &H4
Private Const OFN_LONGNAMES = &H200000                       '  force long names for 3.x modules
Private Const OFN_NOCHANGEDIR = &H8
Private Const OFN_NODEREFERENCELINKS = &H100000
Private Const OFN_NOLONGNAMES = &H40000                      '  force no long names for 4.x modules
Private Const OFN_NONETWORKBUTTON = &H20000
Private Const OFN_NOREADONLYRETURN = &H8000
Private Const OFN_NOTESTFILECREATE = &H10000
Private Const OFN_NOVALIDATE = &H100
Private Const OFN_OVERWRITEPROMPT = &H2
Private Const OFN_PATHMUSTEXIST = &H800
Private Const OFN_READONLY = &H1
Private Const OFN_SHAREAWARE = &H4000
Private Const OFN_SHAREFALLTHROUGH = 2
Private Const OFN_SHARENOWARN = 1
Private Const OFN_SHAREWARN = 0
Private Const OFN_SHOWHELP = &H10
 
Private Type OPENFILENAME
        lStructSize As Long
        hwndOwner As Long
        hInstance As Long
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        flags As Long
        nFileOffset As Integer
        nFileExtension As Integer
        lpstrDefExt As String
        lCustData As Long
        lpfnHook As Long
        lpTemplateName As String
End Type

Private Type BROWSEINFO
    hwndOwner As Long
    pidlRoot As Long
    pszDisplayName As String
    pszTitle As String
    ulFlags As Long
    lpfn As Long
    lParam As Long
    iImage As Long
End Type
 
Private Declare Function GetOpenFileName Lib "comdlg32.dll" Alias "GetOpenFileNameA" (pOpenfilename As OPENFILENAME) As Long
Private Declare Function SHBrowseForFolder Lib "shell32.dll" Alias "SHBrowseForFolderA" (lpBrowseInfo As BROWSEINFO) As Long
Private Declare Function SHGetPathFromIDList Lib "shell32" (ByVal pidList As Long, ByVal lpBuffer As String) As Long
Private Declare Sub Sleep Lib "kernel32" (ByVal dwMilliseconds As Long)

Private diretorio As String
Private lista_componentes As Collection
Private num_componentes
Private num_ligacoes
Private interlig As Collection
Private num_eng As New int_p

Private Function AddBS(ByVal sPath As String) As String
'------------------------------------------------------------------------------------------------------
'  FUNCAO PARA ADICIONAR A BARRA AOS CAMINHOS
'------------------------------------------------------------------------------------------------------
    If Right$(sPath, 1) <> "\" Then sPath = sPath & "\"
    AddBS = sPath
End Function


Private Sub b_carrega_Click()
    l_num_comp.Caption = ""
    l_num_lig.Caption = ""
    
    If Trim(t_file.Value & vbNullString) <> vbNullString Then
        Set lista_componentes = carrega_fiacao(t_file.Value)
        num_componentes = 0
        num_ligacoes = 0
        
        Dim comp As Collection
        Dim term As Collection
        Dim i As Integer
        
        For Each comp In lista_componentes
            'Debug.Print comp("_id_")
            num_componentes = num_componentes + 1
            For i = 2 To comp.Count
                Set term = comp(i)
                'Debug.Print term("terminal") & "-" & term("ligacao") & "<->" & term("cont")
                num_ligacoes = num_ligacoes + 1
                
            Next i
        Next comp
        
        l_num_comp.Caption = "Número de componentes: " & CStr(num_componentes)
        l_num_lig.Caption = "Número de ligações: " & CStr(num_ligacoes)
    End If
End Sub

Private Sub b_coloca_Click()
    If l_cabos.ListIndex >= 0 Then
        Dim nome_cabo As String
        Dim cabo As Collection
        Dim condutores As Collection
        
        
        nome_cabo = l_cabos.List(l_cabos.ListIndex)
        
        
        
        Set cabo = interlig(nome_cabo)
        Set condutores = cabo("cond")
        
        Dim classe As New cl_interlig
        Set classe.lista_interlig = interlig
        classe.rev = "a1"
        Set classe.ck_inv = ck_inverte
        Set classe.ck_y = ck_baixo
        Set classe.engates = num_eng
        Set classe.lista_cabos = l_cabos
        
        CommandState.StartPrimitive classe, True
        
    End If
    
End Sub

Private Sub b_dupli_Click()
    Dim comp As Collection
    Dim term As Collection
    Dim i As Integer
    t_log.Value = "--Ligações duplicadas--" & vbCrLf
    For Each comp In lista_componentes
        For i = 2 To comp.Count
            Set term = comp(i)
            If (term("cont") > 1) Then
                t_log.Value = t_log.Value & comp("_id_") & "." & term("terminal") & vbTab & term("ligacao") & vbCrLf
            End If
            
        Next i
    Next comp
End Sub

Private Sub b_explora_Click()
'------------------------------------------------------------------------------------------------------
'  escolhe um arquivo
'------------------------------------------------------------------------------------------------------
    Dim tOPENFILENAME As OPENFILENAME
    Dim lResult As Long
    Dim vFiles As Variant
    Dim lIndex As Long, lStart As Long
    
    With tOPENFILENAME
        .lpstrTitle = "Escolha o arquivo"
        .flags = OFN_EXPLORER Or OFN_FILEMUSTEXIST Or OFN_LONGNAMES Or OFN_NOCHANGEDIR
        .hwndOwner = 0&
        .nMaxFile = 65535
        .lpstrInitialDir = diretorio
        .lpstrFilter = "Arquivos CSV" & Chr(0) & "*.csv" & Chr(0) & Chr(0)
        .lpstrFile = Space(.nMaxFile - 1) & Chr(0)
        .lStructSize = Len(tOPENFILENAME)
    End With
    
    lResult = GetOpenFileName(tOPENFILENAME)
    
    If lResult > 0 Then
        t_file.Value = Trim$(tOPENFILENAME.lpstrFile)
        diretorio = Left(t_file.Value, InStrRev(t_file.Value, "\"))
    End If

End Sub


Private Sub b_ident_Click()
    If Trim(t_ident.Value & vbNullString) <> vbNullString Then
        fiacao_identifica Trim(t_ident.Value)
    End If
    
End Sub

Private Sub b_inter_arq_Click()
    Dim cabo As Collection
    Dim conds As Collection
    Dim cond As Collection
    Dim i As Integer
    
    
    
    If Trim(t_inter_arq.Value & vbNullString) <> vbNullString Then
        Set interlig = le_interlig(t_inter_arq.Value)
    
        'For Each cabo In interlig
        '    Debug.Print cabo("id") & "-" & cabo("num")
        '    Set conds = cabo("cond")
        '    For Each cond In conds
        '        Debug.Print cond("id") & "," & cond("orig") & "," & cond("dest")
        '    Next cond
        'Next cabo
        
        cabos_usados interlig
        
        l_cabos.Clear
        
        
        
        
        i = 0
        For Each cabo In interlig
            l_cabos.AddItem
            l_cabos.List(i, 0) = cabo("id")
            l_cabos.List(i, 1) = cabo("usados")
            l_cabos.List(i, 2) = cabo("cond").Count
            i = i + 1
        Next cabo
    End If
    
End Sub

Private Sub b_inter_expl_Click()
'------------------------------------------------------------------------------------------------------
'  escolhe um arquivo de interligacao
'------------------------------------------------------------------------------------------------------
    Dim tOPENFILENAME As OPENFILENAME
    Dim lResult As Long
    Dim vFiles As Variant
    Dim lIndex As Long, lStart As Long
    
    With tOPENFILENAME
        .lpstrTitle = "Escolha o arquivo"
        .flags = OFN_EXPLORER Or OFN_FILEMUSTEXIST Or OFN_LONGNAMES Or OFN_NOCHANGEDIR
        .hwndOwner = 0&
        .nMaxFile = 65535
        .lpstrInitialDir = diretorio
        .lpstrFilter = "Arquivos CSV" & Chr(0) & "*.csv" & Chr(0) & Chr(0)
        .lpstrFile = Space(.nMaxFile - 1) & Chr(0)
        .lStructSize = Len(tOPENFILENAME)
    End With
    
    lResult = GetOpenFileName(tOPENFILENAME)
    
    If lResult > 0 Then
        t_inter_arq.Value = Trim$(tOPENFILENAME.lpstrFile)
        diretorio = Left(t_inter_arq.Value, InStrRev(t_inter_arq.Value, "\"))
    End If
End Sub

Private Sub b_n_conect_Click()
    Dim comp As Collection
    Dim term As Collection
    Dim i As Integer
    t_log.Value = "-- Ligações não executadas --" & vbCrLf
    For Each comp In lista_componentes
        For i = 2 To comp.Count
            Set term = comp(i)
            If (term("cont") = 0) Then
                t_log.Value = t_log.Value & comp("_id_") & "." & term("terminal") & vbTab & term("ligacao") & vbCrLf
            End If
            
        Next i
    Next comp
End Sub

Private Sub b_preenche_Click()
    Dim tags
    tags = Array("terminal", "ligacao", "esquematico", "esq_inf", "le", "rev", "num")
   
    If p_preenche.SelectedItem.Index = 0 Then
        If c_preenche.ListIndex < 6 Then
            numera_sequencial tags(c_preenche.ListIndex), CInt(t_ini.Value), CStr(t_prefixo.Value), CStr(t_sufixo.Value)
        Else
            numera_sequencial_secionavel CInt(t_ini.Value), CStr(t_prefixo.Value), CStr(t_sufixo.Value)
        End If
        
    Else
        If c_preenche.ListIndex < 6 Then
            Dim linhas() As String
            linhas = Split(t_preenche_lista.Text, vbCrLf)
            numera_lista linhas, tags(c_preenche.ListIndex)
        End If
    End If
End Sub

Private Sub b_print_Click()
    Dim comp As Collection
    Dim term As Collection
    Dim i As Integer
    t_vis.Value = ""
    For Each comp In lista_componentes
        t_vis.Value = t_vis.Value & "----" & comp("_id_") & "----" & vbCrLf
        For i = 2 To comp.Count
            Set term = comp(i)
            t_vis.Value = t_vis.Value & term("terminal") & vbTab & term("ligacao") & vbCrLf
            
            
        Next i
    Next comp

End Sub

Private Sub b_run_Click()
    
    executa_fiacao lista_componentes, t_rev.Value
    
    Dim executado As Integer
    Dim duplicado As Integer
    Dim comp As Collection
    Dim term As Collection
    Dim i As Integer
    
    
    executado = 0
    duplicado = 0
    l_num_dupli.Caption = ""
    l_num_exec.Caption = ""
    
    If Not (lista_componentes Is Nothing) Then
        For Each comp In lista_componentes
            
            For i = 2 To comp.Count
                Set term = comp(i)
                'Debug.Print term("terminal") & "-" & term("ligacao") & "<->" & term("cont")
                If (term("cont") > 0) Then executado = executado + 1
                If (term("cont") > 1) Then duplicado = duplicado + 1
                
            Next i
        Next comp
        
        l_num_exec.Caption = "Ligações executadas: " & executado
        l_num_dupli.Caption = "Ligações duplicadas: " & duplicado
    End If
    
    
End Sub

Private Sub b_sel_rev_Click()
    If Trim(t_rev.Value & vbNullString) <> vbNullString Then
        selec_rev Trim(t_rev.Value)
    End If
End Sub

Private Sub b_selec_Click()
    If Trim(t_ident.Value & vbNullString) <> vbNullString Then
        selec_fiacao Trim(t_ident.Value)
    End If
    
End Sub

Private Sub t_ini_Change()
    If Not t_ini.Value = "" Then
        If Not IsNumeric(t_ini.Value) Then
            t_ini.Value = "1"
        End If
    End If
End Sub

Private Sub t_ini_Exit(ByVal Cancel As MSForms.ReturnBoolean)
    If Not IsNumeric(t_ini.Value) Then
        t_ini.Value = "1"
    End If
End Sub

Private Sub UserForm_Initialize()
    If ActiveWorkspace.IsConfigurationVariableDefined("FIACAO_DIR") Then
        diretorio = ActiveWorkspace.ConfigurationVariableValue("FIACAO_DIR")
    Else
        diretorio = ""
    End If
    c_preenche.AddItem "Terminal"
    c_preenche.AddItem "Ligação"
    c_preenche.AddItem "Esquematico"
    c_preenche.AddItem "Esq Baixo"
    c_preenche.AddItem "LE"
    c_preenche.AddItem "Revisão"
    c_preenche.AddItem "Secionável"
    c_preenche.ListIndex = 0
    
    l_cab.ColumnCount = 4
    l_cab.ColumnWidths = "45;25;25;15"
    l_cab.AddItem
    l_cab.List(0, 0) = "Cabo"
    l_cab.List(0, 1) = "Des"
    l_cab.List(0, 2) = "Tot"
    l_cabos.ColumnCount = 4
    l_cabos.ColumnWidths = "45;25;25;15"
    
    Set lista_componentes = Nothing
    num_componentes = 0
    num_ligacoes = 0
    num_eng.Value = 1
End Sub

Private Sub UserForm_Terminate()
    ActiveWorkspace.AddConfigurationVariable "FIACAO_DIR", diretorio, True
End Sub

Attribute VB_Name = "int_p"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public Value As Integer

Attribute VB_Name = "m_fiacao"

Function sort_crit(el_a As Element, el_b As Element) As Boolean
    ax = el_a.AsCellElement.Origin.X
    bx = el_b.AsCellElement.Origin.X
    ay = el_a.AsCellElement.Origin.Y
    by = el_b.AsCellElement.Origin.Y
    If (bx = ax) Then
        sort_crit = ay < by
    Else
        sort_crit = ax > bx
    End If
End Function

Sub Quicksort(values() As Element, ByVal min As Long, ByVal max As Long)

  Dim med_value As Element
  Dim hi As Long
  Dim lo As Long
  Dim i As Long

  ' If the list has only 1 item, it's sorted.
  If min >= max Then Exit Sub

  ' Pick a dividing item randomly.
  i = (min + max) \ 2
  Set med_value = values(i)

  ' Swap the dividing item to the front of the list.
  Set values(i) = values(min)

  ' Separate the list into sublists.
  lo = min
  hi = max
  Do
    ' Look down from hi for a value < med_value.
    'Do While values(hi).AsCellElement.Origin.Y - values(hi).AsCellElement.Origin.X < med_value.AsCellElement.Origin.Y - med_value.AsCellElement.Origin.X
    Do While sort_crit(values(hi), med_value)
      hi = hi - 1
      If hi <= lo Then Exit Do
    Loop

    If hi <= lo Then
      ' The list is separated.
      Set values(lo) = med_value
      Exit Do
    End If

    ' Swap the lo and hi values.
    Set values(lo) = values(hi)

    ' Look up from lo for a value >= med_value.
    lo = lo + 1
    'Do While values(lo).AsCellElement.Origin.Y - values(lo).AsCellElement.Origin.X >= med_value.AsCellElement.Origin.Y - med_value.AsCellElement.Origin.X
    Do While sort_crit(med_value, values(lo))
      lo = lo + 1
      If lo >= hi Then Exit Do
    Loop

    If lo >= hi Then
      ' The list is separated.
      lo = hi
      Set values(hi) = med_value
      Exit Do
    End If

    ' Swap the lo and hi values.
    Set values(hi) = values(lo)
  Loop ' Loop until the list is separated.

  ' Recursively sort the sublists.
  Quicksort values, min, lo - 1
  Quicksort values, lo + 1, max

End Sub

Function le_fiacao(path As String)
    Dim componentes As New Collection
    Dim componente As Collection

    Dim linha
    
    Open path For Input As #1    ' Open file.
    Do While Not EOF(1)    ' Loop until end of file.
        Line Input #1, linha    ' Read line into variable.
        If Left(linha, 1) = "#" Then
            If Not (componente Is Nothing) Then
                componentes.Add componente
            End If
            Set componente = New Collection
            componente.Add Mid(linha, 2)
            'Debug.Print linha    ' Print to the Immediate window.
        ElseIf Not (componente Is Nothing) Then
            componente.Add Split(linha, ";")
        
        End If
        
    Loop
    Close #1    ' Close file.
    
    If Not (componente Is Nothing) Then
        componentes.Add componente
    End If
    
    Set le_fiacao = componentes

End Function

Function le_interlig(path As String)
    Dim cabos As New Collection
    Dim cabo As Collection
    Dim conds As Collection
    Dim cond As Collection
    Dim param() As String
    Dim cabo_id As String
    

    Dim linha
    
    Open path For Input As #1    ' Open file.
    Do While Not EOF(1)    ' Loop until end of file.
        Line Input #1, linha    ' Read line into variable.
        If Left(linha, 1) = "#" Then
            If Not (conds Is Nothing) Then
                cabo.Add conds, "cond"
            End If
            If Not (cabo Is Nothing) Then
                cabos.Add cabo, cabo_id
            End If
            Set cabo = New Collection
            param = Split(linha, ";")
            If UBound(param) > 2 Then
                cabo_id = Mid(param(0), 2)
                cabo.Add cabo_id, "id"
                cabo.Add param(1), "num"
                cabo.Add param(2), "descr"
                cabo.Add param(3), "des"
                cabo.Add 0, "usados"
                cabo.Add "", "engate"
            End If
            Set conds = New Collection
            
            
            'Debug.Print linha    ' Print to the Immediate window.
        ElseIf Not (cabo Is Nothing) Then
            param = Split(linha, ";")
            If UBound(param) > 1 Then
                Set cond = New Collection
                
                cond.Add param(0), "id"
                cond.Add param(1), "orig"
                cond.Add param(2), "dest"
                cond.Add 0, "x"
                cond.Add 0, "y"
                cond.Add 0, "usado"
                conds.Add cond
            End If
        
        End If
        
    Loop
    Close #1    ' Close file.
    
    If Not (conds Is Nothing) Then
        cabo.Add conds, "cond"
    End If
    
    If Not (cabo Is Nothing) Then
        cabos.Add cabo, cabo_id
    End If
    
    Set le_interlig = cabos

End Function

'Search a element's tag by its name. Return the found TagElement.
Function get_tag_name(el As Element, tag_name As String) As TagElement
    If (el.HasAnyTags) Then
        Dim oTags() As TagElement
        oTags = el.GetTags() 'get all tags in array
        
        For i = LBound(oTags) To UBound(oTags) 'process tag array
            If (oTags(i).TagDefinitionName = tag_name) Then 'check if name match
                Set get_tag_name = oTags(i) 'return current TagElement
                Exit Function
            End If
        Next i
    End If
    Set get_tag_name = Nothing 'if not found, return nothing
End Function

'Search a element's tag by its name and check if its value match.
Function get_tag_value(el As Element, tag_name As String, tag_value As String) As Boolean
    If (el.HasAnyTags) Then
        Dim oTag As TagElement
        
        Set oTag = get_tag_name(el, tag_name) 'get tag by name
        If Not (oTag Is Nothing) Then
            If (oTag.Value = tag_value) Then 'check if tag value match
                get_tag_value = True 'return success
                Exit Function
            End If
        End If
    End If
    get_tag_value = False 'if not found, return fail
End Function
Function GetTagSet(Name As String) As TagSet
    Dim oTagSets As TagSets
    
    Set oTagSets = ActiveDesignFile.TagSets
    On Error Resume Next
    Set GetTagSet = oTagSets(Name)
    If GetTagSet Is Nothing Then
        Dim td As TagDefinition
        Set GetTagSet = oTagSets.Add(Name)
        Set td = GetTagSet.TagDefinitions.Add(Name, msdTagTypeCharacter)
        'td.IsConstant = True
        td.DefaultValue = Name
    End If
End Function

Sub cell_level(el As Element, level_name As String)
    Set el.Level = ActiveDesignFile.Levels(level_name)
    el.Rewrite
    
    If (el.HasAnyTags) Then
        Dim oTags() As TagElement
        
        oTags = el.GetTags() 'get all tags in array
        
        For i = LBound(oTags) To UBound(oTags) 'process tag array
            Set oTags(i).Level = ActiveDesignFile.Levels(level_name)
            oTags(i).Rewrite
        Next i
    End If
End Sub

Sub match_tag_attr(dest As TagElement, source As TagElement)
    Dim mtrx As Matrix3d
    Dim Rotation1 As Matrix3d
    Dim Rotation2 As Matrix3d
    Dim scaleFactors As Point3d
    Dim xRot As Double, yRot As Double, zRot As Double, uniformScale As Double
    
    
    
    dest.Font = source.Font
    dest.Height = source.Height
    dest.Justification = source.Justification
    
    
    mtrx = source.Rotation
    Matrix3dIsRotateScaleRotate mtrx, Rotation1, scaleFactors, Rotation2
    Matrix3dIsXRotationYRotationZRotationScale Rotation1, xRot, yRot, zRot, uniformScale
    'Debug.Print "     rotation is " & xRot & ", " & yRot & ", " & zRot
    dest.Rotate source.Origin, xRot, yRot, zRot
    
    dest.Move source.Offset
    dest.Width = source.Width
    dest.Color = source.Color
    dest.Level = source.Level
    dest.LineWeight = source.LineWeight
    dest.Redraw msdDrawingModeNormal
    dest.Rewrite
    
End Sub

Private Function existe_valor(col As Collection, key As String) As Boolean
    On Error GoTo compNotFound
    Dim itm As Collection
    Set itm = col(key)
    existe_valor = True
    Exit Function
compNotFound:
    existe_valor = False
    Exit Function
End Function

Sub lista_term()
    Dim oEnumerator As ElementEnumerator
    Dim esc As ElementScanCriteria
    Dim elemento As Element
    Dim tag As TagElement
    Dim term As New Collection
    Dim term_el As Collection
    
    Dim comp_id As String
    Dim term_id As String
    Dim borne_id As String
    
    Set esc = New ElementScanCriteria
    esc.ExcludeAllTypes
    esc.IncludeType msdElementTypeCellHeader
    esc.IncludeType msdElementTypeSharedCell
    
    Set oEnumerator = ActiveModelReference.Scan(esc)

    Do While oEnumerator.MoveNext
        comp_id = ""
        term_id = ""
        Set elemento = oEnumerator.Current
        
        Set tag = get_tag_name(elemento, "id")
        If Not (tag Is Nothing) Then
            comp_id = tag.Value
        End If
        
        Set tag = get_tag_name(elemento, "terminal")
        If Not (tag Is Nothing) Then
            term_id = tag.Value
        End If
        
        If comp_id <> "" And term_id <> "" Then
            borne_id = comp_id & "." & term_id
            If Not existe_valor(term, borne_id) Then
                Set term_el = New Collection
                
                term_el.Add borne_id, "id"
                term_el.Add elemento.AsCellElement.Origin.X, "x"
                term_el.Add elemento.AsCellElement.Origin.Y, "y"
                
                term.Add term_el, borne_id
            End If
        End If
            
    Loop
    
    For Each term_el In term
        Debug.Print term_el("id")
    Next term_el
    
    
End Sub

Sub cabos_usados(cabos As Collection)
    Dim oEnumerator As ElementEnumerator
    Dim esc As ElementScanCriteria
    Dim elemento As Element
    Dim tag As TagElement
    Dim term As New Collection
    Dim term_el As Collection
    Dim cabo As Collection
    Dim conds As Collection
    Dim cond As Collection
    
    Dim comp_id As String
    Dim term_id As String
    Dim borne_id As String
    
    
    Set esc = New ElementScanCriteria
    esc.ExcludeAllTypes
    esc.IncludeType msdElementTypeCellHeader
    esc.IncludeType msdElementTypeSharedCell
    
    Set oEnumerator = ActiveModelReference.Scan(esc)

    Do While oEnumerator.MoveNext
        comp_id = ""
        term_id = ""
        Set elemento = oEnumerator.Current
        
        Set tag = get_tag_name(elemento, "id")
        If Not (tag Is Nothing) Then
            comp_id = tag.Value
        End If
        
        Set tag = get_tag_name(elemento, "terminal")
        If Not (tag Is Nothing) Then
            term_id = tag.Value
        End If
        
        If comp_id <> "" And term_id <> "" Then
            borne_id = comp_id & "." & term_id
            If Not existe_valor(term, borne_id) Then
                Set term_el = New Collection
                
                term_el.Add borne_id, "id"
                term_el.Add elemento.AsCellElement.Origin.X, "x"
                term_el.Add elemento.AsCellElement.Origin.Y, "y"
                
                term.Add term_el, borne_id
            End If
        End If
            
    Loop
    
    'For Each term_el In term
    '    Debug.Print term_el("id")
    'Next term_el
    
    'For Each cabo In cabos
    '    Debug.Print cabo("id") & "-" & cabo("num")
    '    Set conds = cabo("cond")
    '    For Each cond In conds
    '        Debug.Print cond("id") & "," & cond("orig") & "," & cond("dest")
    '    Next cond
    'Next cabo
    
    For Each cabo In cabos
    
        Set conds = cabo("cond")
        For Each cond In conds
            If existe_valor(term, cond("orig")) Then
                
                borne_id = cond("orig")
                Set term_el = term(borne_id)
                
                cond.Remove "usado"
                cond.Add 1, "usado"
                
                cond.Remove "x"
                cond.Add term_el("x"), "x"
                
                cond.Remove "y"
                cond.Add term_el("y"), "y"
                
                usados = cabo("usados") + 1
                cabo.Remove "usados"
                cabo.Add usados, "usados"
                
                
                
            End If
        Next cond
    Next cabo
    
    
    
End Sub

Sub executa_fiacao(componentes As Collection, rev As String)
    If Not (componentes Is Nothing) Then
        Dim oEnumerator As ElementEnumerator
        Dim esc As ElementScanCriteria
        
        Set esc = New ElementScanCriteria
        esc.ExcludeAllTypes
        esc.IncludeType msdElementTypeCellHeader
        esc.IncludeType msdElementTypeSharedCell
        
        Set oEnumerator = ActiveModelReference.Scan(esc)
    
        Do While oEnumerator.MoveNext
            
            Dim elemento As Element
            Dim tag As TagElement
            Dim comp As Collection
            Dim term As Collection
            
            Set elemento = oEnumerator.Current
            
            For Each comp In componentes
                If (get_tag_value(elemento, "id", comp("_id_"))) Then
                    
                    For i = 2 To comp.Count
                        
                        Set term = comp(i)
                        If (get_tag_value(elemento, "terminal", CStr(term("terminal")))) Then
                            Set tag = get_tag_name(elemento, "ligacao")
                            If Not (tag Is Nothing) Then
                                tag.Value = term("ligacao")
                                tag.Redraw
                                tag.Rewrite
                                Set tag = get_tag_name(elemento, "rev")
                                If Not (tag Is Nothing) Then
                                    tag.Value = rev
                                    tag.Redraw
                                    tag.Rewrite
                                End If
                                
                                cont = term("cont") + 1
                                term.Remove "cont"
                                term.Add cont, "cont"
                            End If
                            
                            Exit For
                        End If
                    Next i
                    
                    Exit For
                End If
            Next comp
        Loop
    End If
    
End Sub

Sub selec_fiacao(nome As String)
    
    Dim oEnumerator As ElementEnumerator
    Dim esc As ElementScanCriteria
    Dim oTags() As TagElement
    Dim i As Integer
    
    
    Set esc = New ElementScanCriteria
    esc.ExcludeAllTypes
    esc.IncludeType msdElementTypeCellHeader
    esc.IncludeType msdElementTypeSharedCell
    
    ActiveModelReference.UnselectAllElements
    Set oEnumerator = ActiveModelReference.Scan(esc)

    Do While oEnumerator.MoveNext
        
        Dim elemento As Element
        
        Set elemento = oEnumerator.Current
        If (get_tag_value(elemento, "id", nome)) Then
            ActiveModelReference.SelectElement elemento, True
            'seleciona todos tags associados
            If (elemento.HasAnyTags) Then
                oTags = elemento.GetTags() 'get all tags in array
                
                For i = LBound(oTags) To UBound(oTags) 'process tag array
                    If Not (oTags(i).AsTagElement.IsHidden) Then
                        ActiveModelReference.SelectElement oTags(i), True
                    End If
                Next i
            End If
        End If
    Loop
    
End Sub

Sub selec_rev(rev As String)
    
    Dim oEnumerator As ElementEnumerator
    Dim esc As ElementScanCriteria
    
    Set esc = New ElementScanCriteria
    esc.ExcludeAllTypes
    esc.IncludeType msdElementTypeCellHeader
    esc.IncludeType msdElementTypeSharedCell
    
    ActiveModelReference.UnselectAllElements
    Set oEnumerator = ActiveModelReference.Scan(esc)

    Do While oEnumerator.MoveNext
        
        Dim elemento As Element
        
        Set elemento = oEnumerator.Current
        If (get_tag_value(elemento, "rev", rev)) Then
            ActiveModelReference.SelectElement elemento, True
            'seleciona todos tags associados
            If (elemento.HasAnyTags) Then
                oTags = elemento.GetTags() 'get all tags in array
                
                For i = LBound(oTags) To UBound(oTags) 'process tag array
                    If Not (oTags(i).AsTagElement.IsHidden) Then
                        ActiveModelReference.SelectElement oTags(i), True
                    End If
                Next i
            End If
            
        End If
    Loop
    
End Sub

Sub fiacao_identifica(nome As String)
    
    Dim id As TagElement
    Dim ee As ElementEnumerator
    
    contador = inicial
    Set ee = ActiveModelReference.GetSelectedElements
    Do While ee.MoveNext
        If ee.Current.Type = msdElementTypeCellHeader Or ee.Current.Type = msdElementTypeSharedCell Then
            Set id = get_tag_name(ee.Current, "id")
            If Not (id Is Nothing) Then
                id.Value = nome
                id.Redraw
                id.Rewrite
            End If
        End If
    Loop
End Sub

Sub numera_sequencial(Optional ByVal nome_tag As String = "terminal", _
    Optional ByVal inicial As Integer = 1, _
    Optional ByVal prefixo As String = "", _
    Optional ByVal sufixo As String = "")
    
    Dim id As TagElement
    Dim ee As ElementEnumerator
    Dim contador As Integer
    Dim i As Integer
    Dim lista() As Element
    
    'cria uma lista com os elementos selecionados
    i = 0
    Set ee = ActiveModelReference.GetSelectedElements
    Do While ee.MoveNext
        ' na lista so existem elementos do tipo cell
        If ee.Current.Type = msdElementTypeCellHeader Or ee.Current.Type = msdElementTypeSharedCell Then
            ReDim Preserve lista(i + 1)
            Set lista(i) = ee.Current
            i = i + 1
        End If
    Loop
    If Not Not lista Then
        'ordena a lista pela posicao do elemento (de cima para baixo e da esqueda para direita)
        Quicksort lista, LBound(lista), UBound(lista) - 1
        
        'executa a numeracao, varrendo a lista de elementos ordenada
        contador = inicial
        For i = LBound(lista) To UBound(lista) - 1
            Set id = get_tag_name(lista(i), nome_tag)
            If Not (id Is Nothing) Then
                id.Value = prefixo & CStr(contador) & sufixo
                id.Redraw
                id.Rewrite
                
                contador = contador + 1
            End If
        Next i
    End If
End Sub

Sub numera_sequencial_secionavel(Optional ByVal inicial As Integer = 1, _
    Optional ByVal prefixo As String = "", _
    Optional ByVal sufixo As String = "")
    
    Dim id As TagElement
    Dim ee As ElementEnumerator
    Dim cont_e As Integer
    Dim cont_s As Integer
    Dim cont_c As Integer
    Dim i As Integer
    Dim lista() As Element
    
    'cria uma lista com os elementos selecionados
    i = 0
    Set ee = ActiveModelReference.GetSelectedElements
    Do While ee.MoveNext
        ' na lista so existem elementos do tipo cell
        If ee.Current.Type = msdElementTypeCellHeader Or ee.Current.Type = msdElementTypeSharedCell Then
            ReDim Preserve lista(i + 1)
            Set lista(i) = ee.Current
            i = i + 1
        End If
    Loop
    If Not Not lista Then
        'ordena a lista pela posicao do elemento (de cima para baixo e da esqueda para direita)
        Quicksort lista, LBound(lista), UBound(lista) - 1
        
        'executa a numeracao, varrendo a lista de elementos ordenada
        cont_e = inicial
        cont_s = inicial
        cont_c = inicial
        For i = LBound(lista) To UBound(lista) - 1
            If lista(i).AsCellElement.Name = "sec_e" Then
                Set id = get_tag_name(lista(i), "terminal")
                If Not (id Is Nothing) Then
                    id.Value = prefixo & CStr(cont_e) & sufixo & "E"
                    id.Redraw
                    id.Rewrite
                    
                    cont_e = cont_e + 1
                End If
            ElseIf lista(i).AsCellElement.Name = "sec_s" Then
                Set id = get_tag_name(lista(i), "terminal")
                If Not (id Is Nothing) Then
                    id.Value = prefixo & CStr(cont_s) & sufixo & "S"
                    id.Redraw
                    id.Rewrite
                    
                    cont_s = cont_s + 1
                End If
            ElseIf lista(i).AsCellElement.Name = "sec_central" Then
                Set id = get_tag_name(lista(i), "num")
                If Not (id Is Nothing) Then
                    id.Value = prefixo & CStr(cont_c) & sufixo
                    id.Redraw
                    id.Rewrite
                    
                    cont_c = cont_c + 1
                End If
            End If
        Next i
    End If
End Sub

Sub numera_lista(lista() As String, Optional ByVal nome_tag As String = "terminal")
    
    Dim id As TagElement
    Dim ee As ElementEnumerator
    Dim contador As Integer
    Dim ini As Integer
    Dim fim As Integer
    Dim i As Integer
    Dim lista_el() As Element
    
    'cria uma lista com os elementos selecionados
    i = 0
    Set ee = ActiveModelReference.GetSelectedElements
    Do While ee.MoveNext
        ' na lista so existem elementos do tipo cell
        If ee.Current.Type = msdElementTypeCellHeader Or ee.Current.Type = msdElementTypeSharedCell Then
            ReDim Preserve lista_el(i + 1)
            Set lista_el(i) = ee.Current
            i = i + 1
        End If
    Loop
    If (Not Not lista_el) And (UBound(lista) >= 0) Then
        'ordena a lista pela posicao do elemento (de cima para baixo e da esqueda para direita)
        Quicksort lista_el, LBound(lista_el), UBound(lista_el) - 1
        
        ini = LBound(lista)
        fim = UBound(lista)
        contador = ini
        'executa a numeracao, varrendo a lista de elementos ordenada
        For i = LBound(lista_el) To UBound(lista_el) - 1
            Set id = get_tag_name(lista_el(i), nome_tag)
            If Not (id Is Nothing) Then
                If Trim(lista(contador) & vbNullString) <> vbNullString Then
                    id.Value = Trim(lista(contador))
                    id.Redraw
                    id.Rewrite
                End If
                contador = contador + 1
                If contador > fim Then contador = ini
            End If
        Next i
    End If
End Sub

Private Function check_comp(col As Collection, key As String) As Boolean
    On Error GoTo compNotFound
    Dim itm
    Set itm = col(key)
    check_comp = True
    Exit Function
compNotFound:
    check_comp = False
    Exit Function
End Function

Private Function check_term(col As Collection, key As String) As Boolean
    On Error GoTo termNotFound
    Dim itm
    itm = col(key)
    check_term = True
    Exit Function
termNotFound:
    check_term = False
    Exit Function
End Function
Function carrega_fiacao(arquivo As String) As Collection
    Dim linha
    Dim ligacoes As Collection
    Dim celulas
    Dim pares As New Collection
    Dim componentes As New Collection
    Dim componente As Collection
    Dim campos(0 To 1) As String
    Dim ident As String
    Dim terminal As String
    Dim lig As Collection
    
    
    '--------------------------------------------------------------------------------------------------------
    ' Abre o arquivo separado por virgulas (.csv) e monta os pares de ligaçoes um uma colecao
    '--------------------------------------------------------------------------------------------------------
    Open arquivo For Input As #1 'abre o arquivo
    Do While Not EOF(1)    ' varre o arquivo até o fim
        Line Input #1, linha    ' le uma linha
        celulas = Split(linha, ";") ' monta um vetor com os valores separados por ponto-virgula (;)
        'If (UBound(celulas) > 0) Then ' deve haver pelo menos um par
            Set ligacoes = New Collection
            For i = 0 To UBound(celulas)
                If Trim(celulas(i) & vbNullString) <> vbNullString Then ligacoes.Add celulas(i)
            Next i
            For i = 2 To ligacoes.Count
                pares.Add Array(ligacoes(i - 1), ligacoes(i)) ' monta os pares
            Next i
        'End If
    Loop
    Close #1    ' fecha o arquivo.
    
    
    '--------------------------------------------------------------------------------------------------------
    ' cadastra os componentes em uma colecao e seus respectivos terminais em uma sub-colecao
    '--------------------------------------------------------------------------------------------------------
    For Each par In pares ' varre os pares
    
        For i = 0 To 1 ' analiza cada elemento do par
            ' separa a identificacao do componete e o terminal, separados pelo "."
            campos(0) = Left(par(i), InStr(par(i), ".") - 1)
            campos(1) = Right(par(i), Len(par(i)) - InStr(par(i), "."))
            
            If (UBound(campos) > 0) Then
                ident = UCase(campos(0))
                terminal = UCase(campos(1))
                Set componente = Nothing
                If Not (check_comp(componentes, "id_" & ident)) Then
                    Set componente = New Collection
                    componente.Add ident, "_id_"
                    componentes.Add componente, "id_" & ident
                Else
                    Set componente = componentes("id_" & ident)
                End If
                
                If Not (componente Is Nothing) Then
                    'If Not (check_term(componente, "t_" & terminal)) Then
                        'componente.Add Array(terminal, UCase(par(1 - i))), "t_" & terminal
                    If Not (check_comp(componente, "t_" & terminal)) Then
                        Set lig = New Collection
                        lig.Add terminal, "terminal"
                        lig.Add UCase(par(1 - i)), "ligacao"
                        lig.Add 0, "cont"
                        
                        componente.Add lig, "t_" & terminal
                    Else
                        Set lig = componente("t_" & terminal)
                        texto = lig("ligacao") & "/" & UCase(par(1 - i))
                        lig.Remove ("ligacao")
                        lig.Add texto, "ligacao"
                    End If
                End If
                
            End If
        Next i
    Next par
    
    Set carrega_fiacao = componentes
End Function


Sub abre_janela()
    Load f_fiacao
    f_fiacao.Show 0
    
End Sub
